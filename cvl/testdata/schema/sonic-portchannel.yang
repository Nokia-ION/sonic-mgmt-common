module sonic-portchannel {
    namespace "http://github.com/Azure/sonic-portchannel";
    prefix spc;

    import sonic-common {
        prefix scommon;
    }

    import sonic-port {
        prefix prt;
    }

    organization
        "SONiC";

    contact
        "SONiC";

    description
        "SONIC PORTCHANNEL";

    revision 2019-05-15 {
        description
            "Initial revision.";
    }

    container sonic-portchannel {

        container PORTCHANNEL {

            list PORTCHANNEL_LIST {
                key "name";

                leaf name {
                    type string;
                }

                leaf admin_status {
                    type scommon:admin-status;
                }

                leaf mtu {
                    type uint32 {
                        range "1312..9216" {
                            error-message "Invalid MTU value";
                            error-app-tag mtu-invalid;
                        }
                    }
                }

                leaf min_links {
                    type uint8;
                }

                leaf fallback {
                    type boolean;
                }

                leaf fallback_timeout {
                    type uint16 {
                        range 1..65535;
                    }
                }

                leaf active {
                    type boolean;
                }
            }
        }

        container PORTCHANNEL_MEMBER {

            list PORTCHANNEL_MEMBER_LIST {
                key "name ifname";

                leaf name {
                    type leafref {
                        path "../../../PORTCHANNEL/PORTCHANNEL_LIST/name";
                    }
                }

                leaf ifname {
                    type leafref {
                        path "/prt:sonic-port/prt:PORT/prt:PORT_LIST/prt:ifname";
                    }
                }
            }
        }

        container LAG_TABLE {
            config false;

            list LAG_TABLE_LIST {
                key "lagname";

                leaf lagname {
                    type string;
                }

                leaf admin_status {
                    type scommon:admin-status;
                }

                leaf mtu {
                    type uint32 {
                        range "1312..9216" {
                            error-message "Invalid MTU value";
                            error-app-tag mtu-invalid;
                        }
                    }
                }

                leaf active {
                    type boolean;
                }

                leaf name {
                    type string;
                }

                leaf oper_status {
                    type scommon:oper-status;
                }
            }
        }

        container LAG_MEMBER_TABLE {
            config false;
            list LAG_MEMBER_TABLE_LIST {
                key "name ifname";

                leaf name {
                    type leafref {
                        path "../../../LAG_TABLE/LAG_TABLE_LIST/lagname";
                    }
                }

                leaf ifname {
                    type leafref {
                        path "/prt:sonic-port/prt:PORT/prt:PORT_LIST/prt:ifname";
                    }
                }
            }
        }
    }
}
