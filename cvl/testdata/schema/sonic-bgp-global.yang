module sonic-bgp-global {
    namespace "http://github.com/Azure/sonic-bgp-global";
    prefix sbgpg;
    yang-version 1.1;

    import sonic-vrf {
        prefix svrf;
    }

    import sonic-port {
        prefix prt;
    }

    import ietf-inet-types {
        prefix inet;
    }

    organization
        "SONiC";

    contact
        "SONiC";

    description
        "SONIC BGP Global YANG";

    revision 2019-11-20 {
        description
            "Added BGP fields for extensive features.";
    }

    revision 2019-09-15 {
        description
            "Initial revision.";
    }

    container sonic-bgp-global {
        container BGP_GLOBALS {
            list BGP_GLOBALS_LIST {
                key "vrf_name";

                leaf vrf_name {
                    type union {
                        type string {
                            pattern "default";
                        }
                        type leafref {
                            path "/svrf:sonic-vrf/svrf:VRF/svrf:VRF_LIST/svrf:vrf_name";
                        }
                    }
                }

                leaf router_id {
                    type inet:ipv4-address;
                }

                leaf local_asn {
                    type uint32;
                }

                leaf always_compare_med {
                    type boolean;
                }

                leaf load_balance_mp_relax {
                    type boolean;
                }

                leaf graceful_restart_enable {
                    type boolean;
                }

                leaf gr_preserve_fw_state {
                    type boolean;
                    description
                        "Set F-bit indication that FIB is preserved while doing Graceful Restart.";
                }

                leaf gr_restart_time {
                    type uint16 {
                        range "1..3600";
                    }
                }

                leaf gr_stale_routes_time {
                    type uint16 {
                        range "1..3600";
                    }
                }

                leaf external_compare_router_id {
                    type boolean;
                }

                leaf ignore_as_path_length {
                    type boolean;
                }

                leaf log_nbr_state_changes {
                    type boolean;
                }

                leaf rr_cluster_id {
                    type string;
                }

                leaf rr_allow_out_policy {
                    type boolean;
                }

                leaf disable_ebgp_connected_rt_check {
                    type boolean;
                }

                leaf fast_external_failover {
                    type boolean;
                }

                leaf network_import_check {
                    type boolean;
                }

                leaf graceful_shutdown {
                    type boolean;
                }

                leaf route_flap_dampen {
                    type boolean;
                }

                leaf route_flap_dampen_half_life {
                    type uint8 {
                        range "1..45";
                    }
                }

                leaf route_flap_dampen_reuse_threshold {
                    type uint16 {
                        range "1..20000";
                    }
                }

                leaf route_flap_dampen_suppress_threshold {
                    type uint16 {
                        range "1..20000";
                    }
                }

                leaf route_flap_dampen_max_suppress {
                    type uint8 {
                        range "1..255";
                    }
                }

                leaf rr_clnt_to_clnt_reflection {
                    type boolean;
                    description
                        "Enable client to client route reflection.";
                }

                leaf max_dynamic_neighbors {
                    type uint16 {
                        range 1..5000;
                    }
                    description
                        "Maximum number of BGP dynamic neighbors that can be created.";
                }

                leaf read_quanta {
                    type uint8 {
                        range 1..10;
                    }
                    description
                        "This indicates how many packets to read from peer socket per I/O cycle";
                }

                leaf write_quanta {
                    type uint8 {
                        range 1..64;
                    }
                    description
                        "This indicates how many packets to write to peer socket per run";
                }

                leaf coalesce_time {
                    type uint32;
                    description
                        "Subgroup coalesce timer value in milli-sec";
                }

                leaf route_map_process_delay {
                    type uint16 {
                        range 0..600;
                    }
                    description
                        "0 disables the timer, no route updates happen when route-maps change";
                }

                leaf deterministic_med {
                    type boolean;
                    description
                        "Pick the best-MED path among paths advertised from the neighboring AS.";
                }

                leaf med_confed {
                    type boolean;
                    description
                        "Compare MED among confederation paths when set to true.";
                }

                leaf med_missing_as_worst {
                    type boolean;
                    description
                        "Treat missing MED as the least preferred one when set to true.";
                }

                leaf compare_confed_as_path {
                    type boolean;
                    description
                        "Compare path lengths including confederation sets & sequences in selecting a route";
                }

                leaf as_path_mp_as_set {
                    type boolean;
                    description
                        "Generate an AS_SET.";
                }

                leaf default_ipv4_unicast {
                    type boolean;
                    description
                        "Activate ipv4-unicast for a peer by default";
                }

                leaf default_ipv6_unicast {
                    type boolean;
                    description
                        "Activate ipv6-unicast for a peer by default";
                }

                leaf max_ebgp_paths {
                    type uint16 {
                        range "1..256";
                    }
                    description
                        "Maximum number of equal-cost eBGP paths to install for multipath forwarding at the BGP instance.";
                    default 1;
                }

                leaf max_ibgp_paths {
                    type uint16 {
                        range "1..256";
                    }
                    description
                        "Maximum number of equal-cost iBGP paths to install for multipath forwarding at the BGP instance.";
                    default 1;
                }

                leaf ibgp_equal_cluster_length {
                    type boolean;
                    description
                        "Require matching cluster-list length when comparing iBGP multipath candidates.";
                }

                leaf default_local_preference {
                    type uint32;
                    description
                        "Configure default local preference value.";
                }

                leaf default_show_hostname {
                    type boolean;
                    description
                        "Show hostname in BGP dumps.";
                }

                leaf default_shutdown {
                    type boolean;
                    description
                        "Apply administrative shutdown to newly configured peers.";
                }

                leaf default_subgroup_pkt_queue_max {
                    type uint8 {
                        range 20..100;
                    }
                    description
                        "Configure subgroup packet queue max.";
                }

                leaf max_med_time {
                    type uint32{
                        range 5..86400;
                    }
                    description
                        "Time (seconds) period for max-med";
                }
                
                leaf max_med_val {
                    type uint32;
                    description
                        "Max MED value to be used";
                }

                leaf max_delay {
                    type uint16 {
                        range 0..3600;
                    }
                    description
                        "Maximum delay for best path calculation.";
                }

                leaf establish_wait {
                    type uint16 {
                        range 0..3600;
                    }
                    description
                        "Maximum delay for updates.";
                }
            }
        }
        container EVPN_ETHERNET_SEGMENT {
            list EVPN_ETHERNET_SEGMENT_LIST {
                key "name";
                leaf name {
                    type string;
                }
                leaf ifname {
                    type leafref {
                        path "/prt:sonic-port/prt:PORT/prt:PORT_LIST/prt:ifname";
                    }
                    must "count(../../EVPN_ETHERNET_SEGMENT_LIST[name!=current()/../name][ifname=current()]) = 0";
                }
                leaf delay-time {
                    type uint16;
                }
            }
        }
    }
}
