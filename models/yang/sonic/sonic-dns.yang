module sonic-dns {

    namespace "http://github.com/sonic-net/sonic-dns";
    prefix dns;

    import ietf-inet-types {
        prefix inet;
    }

    description
        "DNS resolver YANG module for SONiC OS.
         Minimal model used by CVL to validate translib writes to the
         DNS_NAMESERVER and DNS_OPTIONS tables driven by the OpenConfig
         /system/dns/servers and /system/dns/config paths.";

    revision 2023-02-14 {
        description
            "First revision";
    }

    container sonic-dns {

        container DNS_NAMESERVER {

            description "DNS nameserver addresses for name resolution.";

            list DNS_NAMESERVER_LIST {
                max-elements 3;
                description "Ordered list of DNS nameserver IP addresses.";

                key "ip";

                leaf ip {
                    type inet:host;
                    description "IPv4 or IPv6 address of a DNS nameserver.";
                }

            }

        }

        container DNS_OPTIONS {

            description "DNS resolver options.";

            /* No defaults: resolv.conf.j2 writes an options entry for every
               field present in the row, and a default would be filled into
               the row when translib creates it. */
            container GLOBAL {

                leaf-list search {
                    type inet:host;
                    description "Ordered list of domains to search when resolving a host name.";
                }

                leaf ndots {
                    type uint8 {
                        range "0..15";
                    }
                    description "Number of dots a name must have before an initial absolute query is made.";
                }

                leaf timeout {
                    type uint8 {
                        range "1..30";
                    }
                    description "Seconds to wait for a name server before retrying with another.";
                }

                leaf attempts {
                    type uint8 {
                        range "1..5";
                    }
                    description "Number of times a query is sent to the name servers before giving up.";
                }

            }

        }

    }

}
