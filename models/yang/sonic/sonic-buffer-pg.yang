module sonic-buffer-pg {
    namespace "http://github.com/Azure/sonic-buffer-pg";
    prefix bpg;

    import sonic-extension {
        prefix sonic-ext;
    }

    import sonic-port {
        prefix prt;
    }

    import sonic-buffer-profile {
        prefix bpf;
    }

    organization
        "SONiC";

    contact
        "SONiC";

    description
        "SONIC BUFFER PG";

    revision 2025-09-22 {
        description
            "Initial revision.";
    }


    container sonic-buffer-pg {

        container BUFFER_PG {

            list BUFFER_PG_LIST {
                key "ifname pg_num";
                sonic-ext:key-pattern "BUFFER_PG|{ifname}|{pg_num}"; //special pattern used for extracting keys from

                leaf ifname {
                    type leafref {
                        path "/prt:sonic-port/prt:PORT/prt:PORT_LIST/prt:ifname";
                    }
                }

                leaf pg_num {
                    type string {
                        pattern "[0-7]((-)[0-7])?" {
                            error-message "Invalid Buffer PG number, expected either single pg number between 0 to 7 or combined 0-7";
                            error-app-tag pg-num-invalid;
                        }
                    }
                }

                leaf profile {
                    type string;
                    description
                      "Refers to a hash profile defined by buffer allocation profile in BUFFER_PROFILE";
                }

                leaf lossless_enable {
                    type boolean;
                    description
                      "Set to true to enable lossless config for ingress priority group.";
                }
            }
        }
    }
}
