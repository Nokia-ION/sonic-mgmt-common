module sonic-port-breakout {
    namespace "http://github.com/Azure/sonic-port-breakout";
    prefix sbrkprt;

    import sonic-port {
        prefix prt;
    }

    import sonic-extension {
        prefix sonic-ext;
    }

    organization
        "SONiC";

    contact
        "SONiC";

    description
        "SONiC Port Breakout";

    revision 2020-03-12 {
        description
            "Initial revision.";
    }

    container sonic-port-breakout {

        container BREAKOUT_CFG {

            list BREAKOUT_CFG_LIST {

                key "ifname";

                leaf ifname {
                    description
                        "A port's primary interface name (which is used to store
                        breakout information for the entire port).
                        This port does not necessarily need to be realized/setup
                        (ie: no corresponding PORT entry)";
                    type string {
                        pattern "(^Ethernet.*)";
                    }
                }

                leaf port {
                    type string;
                }

                leaf brkout_mode {
                    description
                        "Breakout mode in the format of NxSpeed (e.g., 1x100G, 4x25G).
                        Mixed modes may use separators (e.g., 2x100G(4)_1x200G(4)).";
                    type string;
                }
                leaf lanes {
                    type string;
                }
                leaf name {
                    type string {
                        pattern "1/([1-3][0-9]{3}|[1-9][0-9]{2}|[1-9][0-9]|[0-9])";
                    }
                }
                leaf port-id {
                    type uint32;
                }
            }
        }

        container BREAKOUT_PORTS {

            list BREAKOUT_PORTS_LIST {

                key "ifname";

                leaf ifname {
                    type string {
                        pattern "(^Ethernet.*)";
                    }
                }

                leaf master {
                    type string;
                }
            }
        }

        container PORT_STATE {

            list PORT_STATE_LIST {

                key "ifname";

                leaf ifname {
                    type string {
                        pattern "(^Ethernet.*)";
                    }
                }

                leaf phase {
                    type string;
                }

                leaf timestamp {
                    type string;
                }
            }
        }

        container PORT_UNLOCK {

            list PORT_UNLOCK_LIST {

                key "ifname";

                leaf ifname {
                    type string {
                        pattern "(^Ethernet.*)";
                    }
                }
            }
        }

        container BREAKOUT_PORT_XCVR_CFG {

            list BREAKOUT_PORT_XCVR_CFG_LIST {

                key "portname ifname";

                leaf portname {
                    type string {
                        pattern "1/([1-3][0-9]{3}|[1-9][0-9]{2}|[1-9][0-9]|[0-9])";
                    }
                }
                leaf ifname {
                    type string {
                        pattern "(^Ethernet.*)";
                    }
                }
            }
        }

        container PORT_BREAKOUT {
            sonic-ext:db-name "STATE_DB";
            sonic-ext:key-delim "|";
            config false;
            list PORT_BREAKOUT_LIST {
                key "ifname";
                leaf ifname {
                    type string {
                        pattern "(^Ethernet.*)";
                    }
                }

                leaf status {
                    type string;
                }

                leaf name {
                    type string {
                        pattern "1/([1-3][0-9]{3}|[1-9][0-9]{2}|[1-9][0-9]|[0-9])";
                    }
                }

                leaf parent {
                    type string;
                }
                leaf port-id {
                    type uint32;
                }
            }
        }
    }

    rpc breakout_dependencies {

        description "RPC for showing dependencies on breakout port
        input is Ethernet interface";

        input {
            leaf ifname {
                type leafref {
                    path "/prt:sonic-port/prt:PORT/prt:PORT_LIST/prt:ifname";
                }
            }
        }

        output {
            leaf-list keys {
                type string;
                description
                    "On success, returns list of dependent table keys";
            }
        }
    }

    rpc breakout_capabilities {

        description "RPC for listing the breakout capabilities of ports
        input is Ethernet interface";

        input {
            leaf ifname {
                type leafref {
                    path "/prt:sonic-port/prt:PORT/prt:PORT_LIST/prt:ifname";
                }
            }
        }

        output {
            list caps {
                leaf port {
                    type string;
                }
                leaf modes {
                    type string;
                }
                leaf defmode {
                    type string;
                }
            }
        }
    }
}
