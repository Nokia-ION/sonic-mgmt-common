module sonic-ntp {

    namespace "http://github.com/sonic-net/sonic-system-ntp";
    prefix ntp;

    import ietf-inet-types {
        prefix inet;
    }

    description
        "NTP yang Module for SONiC OS";

    revision 2021-04-07 {
        description
            "First revision";
    }

    container sonic-ntp {

        container NTP {
            description "NTP global configuration container.";

            container global {
                description "Global NTP client settings.";

                leaf src_intf {
                    type string;
                    description
                        "Source interface (e.g. Loopback0) whose IP address is
                         used as the source address for generating NTP traffic.
                         Equivalent to EOS 'ntp local-interface'. Stored as a
                         scalar to match the chrony backend and init config.";
                }
            }
        }

        container NTP_SERVER {

            description "NTP Server configuration table.";

            list NTP_SERVER_LIST {
                max-elements 10;
                description
                    "Number of upstream NTP servers is discussed at
                     https://support.ntp.org/bin/view/Support/SelectingOffsiteNTPServers
                     (5.3.4. Excessive Number of Upstream Time Servers).";

                key "server_address";

                leaf server_address {
                    type inet:host;
                    description "IP address of the NTP server";
                }

            }

        }

    }

}
