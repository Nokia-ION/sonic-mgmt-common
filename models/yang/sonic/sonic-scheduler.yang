module sonic-scheduler {
    namespace "http://github.com/Azure/sonic-scheduler";
    prefix sch;

    organization
        "SONiC";

    contact
        "SONiC";

    description
        "SONIC SCHEDULER";

    revision 2026-09-28 {
        description
            "Allow <policy>@<sequence>@<input> names, one scheduler per input
            of a sequence that feeds several queues.";
    }

    revision 2019-05-15 {
        description
            "Initial revision.";
    }

    container sonic-scheduler {

        container SCHEDULER {

            list SCHEDULER_LIST {
                key "name";

                leaf name{
                    type string {
                        pattern "[a-zA-Z0-9]{1}([-a-zA-Z0-9_]{0,31})|[a-zA-Z0-9]{1}([-a-zA-Z0-9_]{0,31})([@]{1})([0-9]{1,3})|[a-zA-Z0-9]{1}([-a-zA-Z0-9_]{0,31})([@]{1})([0-9]{1,3})([@]{1})([-a-zA-Z0-9_]{1,64})";
                        length 1..101;
                    }
                }
                leaf id{
                    type string {
                        length 1..64;
                    }
                }
                leaf queue{
                    type string {
                       length 1..64;
                    }
                }
                leaf type {
                    type enumeration {
                        enum DWRR;
                        enum WRR;
                        enum STRICT;
                    }
                }
                leaf input-type {
                    type enumeration {
                        enum QUEUE;
                        enum IN_PROFILE;
                        enum OUT_PROFILE;
                    }
                }
                leaf weight {
                    type uint8 {
                        range "0..255";
                    }
                }

                leaf priority {
                    type uint8 {
                        range "0..9";
                    }
                }

                leaf meter_type {
                    type enumeration {
                        enum packets;
                        enum bytes;
                    }
                }

                leaf cir {
                  type uint64;
                  units Bps;
                  description
                        "Committed information rate for the dual-rate token
                        bucket policer.  This value represents the rate at which
                        tokens are added to the primary bucket.";
                }

                leaf pir {
                  type uint64;
                  units Bps;
                  description
                        "Peak information rate for the dual-rate token bucket
                        policer.  This value represents the rate at which tokens
                        are added to the secondary bucket.";
                }

                leaf cbs {
                  type uint32;
                  units bytes;
                  description
                        "Committed burst size for the dual-rate token bucket
                        policer.  This value represents the depth of the token
                        bucket.";
                }

                leaf pbs {
                  type uint32;
                  units bytes;
                  description
                        "Excess burst size for the dual-rate token bucket policer.
                        This value represents the depth of the secondary bucket.";
                }
            }
        }
    }
}
