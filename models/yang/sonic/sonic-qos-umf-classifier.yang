module sonic-qos-umf-classifier {
    namespace "http://github.com/Azure/sonic-qos-umf-classfier-group";
    prefix dtm;

    organization
        "SONiC";

    contact
        "SONiC";

    description
        "SONIC QOS_UMF_CLASSIFIER";

    revision 2026-09-28 {
        description
        "Add QOS_UMF_CLASSIFIER_TERM, the terms of a DSCP classifier.";
    }

    revision 2021-04-21 {
        description
        "Initial revision.";
    }

    container sonic-qos-umf-classifier {
        container QOS_UMF_CLASSIFIER {
            list QOS_UMF_CLASSIFIER_LIST {
                key "name";
                description
                  "List of classifiers";

                leaf name {
                    type string;
                }

                leaf type {
                    type enumeration {
                        enum ipv4;
                        enum ipv6;
                    }
                }
            }
        }

        container QOS_UMF_CLASSIFIER_TERM {
            list QOS_UMF_CLASSIFIER_TERM_LIST {
                key "name id";
                description
                  "Terms of a classifier held in DSCP_TO_TC_MAP. The map keeps
                  only DSCP to traffic class pairs; this records which term
                  named which DSCP values, and through which leaf.";

                leaf name {
                    type string;
                }

                leaf id {
                    type string;
                }

                leaf dscp {
                    type uint8 {
                        range "0..63";
                    }
                }

                leaf-list dscp_set {
                    type uint8 {
                        range "0..63";
                    }
                }
            }
        }
    }
}
