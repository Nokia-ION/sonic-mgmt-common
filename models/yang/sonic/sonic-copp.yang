module sonic-copp {

	yang-version 1.1;

	namespace "http://github.com/sonic-net/sonic-copp";
	prefix copp;

	organization
		"SONiC";

	contact
		"SONiC";

	description
		"SONIC CoPP (Control Plane Policing).

		COPP_GROUP names a policer, and the CPU queue packets it polices are
		delivered on; COPP_TRAP binds a set of trap identifiers to one such
		group. coppmgr renders the two tables into the SAI hostif trap and
		trap-group objects, so a group's cir/cbs bound the rate at which its
		traps reach the CPU. This is what restricts, for example, a BGP TCP
		SYN flood: the bgp trap is bound to a group whose policer caps
		BGP-to-CPU traffic, while already-established sessions stay permitted
		by the control-plane firewall rather than by this policer.

		The default entries ship in files/image_config/copp/copp_cfg.j2, which
		is loaded into CONFIG_DB at boot. Exposing the same two tables here
		lets the rates be tuned at run time over gNMI.

		The upstream sonic-copp in sonic-yang-models takes meter_type,
		policer_color_source and policer_packet_action from sonic-types. Those
		are inlined here instead of imported, for the same reason sonic-policer
		inlines them: a local model that imports a SONICYANG_IMPORTS module has
		to be listed in SONIC_YANG_DEFERRED_NAMES to be copied in the right
		order, and inlining keeps this model self-contained.";

	revision 2026-09-03 {
		description
			"Initial revision.";
	}

	/*
	 * The enumerations below are spelled in lower case to match sonic-types,
	 * which is what CVL in sonic-yang-models validates CONFIG_DB against. The
	 * two schema copies have to agree or a value accepted here is rejected
	 * there. coppmgr itself normalises case before use.
	 */
	typedef copp_meter_type {
		description "Policer metering unit: packets or bytes.";
		type enumeration {
			enum packets;
			enum bytes;
		}
	}

	typedef copp_color_source {
		description "Policer color-awareness mode.";
		type enumeration {
			enum aware;
			enum blind;
		}
	}

	typedef copp_packet_action {
		description
			"Action applied by the policer to conforming or violating packets.";
		type enumeration {
			enum drop;
			enum forward;
			enum copy;
			enum copy_cancel;
			enum trap;
			enum log;
			enum deny;
			enum transit;
		}
	}

	container sonic-copp {

		container COPP_GROUP {

			description
				"CoPP groups that rate-limit traffic destined to the CPU.";

			list COPP_GROUP_LIST {

				description
					"A named CoPP group with a CPU queue, trap action, and
					policer settings.";
				key name;

				leaf name {
					type string;
					description "Control plane policing group name.";
				}

				leaf queue {
					type uint32;
					default 0;
					description
						"CPU receive queue number; higher values indicate higher
						priority.";
				}

				leaf trap_priority {
					type uint32;
					default 0;
					description
						"Priority assigned to the trap; higher values are matched
						first.";
				}

				leaf trap_action {
					type copp_packet_action;
					description
						"Action applied to trapped packets (forward, drop, copy,
						etc.).";
				}

				leaf meter_type {
					type copp_meter_type;
					description
						"Metering unit for the embedded policer (packets or
						bytes).";
				}

				leaf mode {
					type enumeration {
						enum sr_tcm;
						enum tr_tcm;
						enum storm;
					}
					description
						"Policer mode: single-rate TCM, two-rate TCM, or storm
						control.";
				}

				leaf color {
					type copp_color_source;
					description "Policer color awareness mode (aware or blind).";
				}

				leaf cir {
					type uint64;
					default 0;
					description
						"Committed information rate: the rate at which tokens are
						added to the primary bucket.";
				}

				leaf cbs {
					must "((current()/../cir) and (current()/../cir > 0))" {
						error-message "cbs can't be configured without cir.";
					}
					must "(current() >= current()/../cir)" {
						error-message "cbs must be greater than or equal to cir";
					}
					type uint64;
					default 0;
					description
						"Committed burst size: the depth of the primary token
						bucket.";
				}

				leaf pir {
					when "current()/../mode = 'tr_tcm'";
					must "((current()/../cir) and (current()/../cir > 0))" {
						error-message "pir can't be configured without cir.";
					}
					must "(current() >= current()/../cir)" {
						error-message "pir must be greater than or equal to cir";
					}
					type uint64;
					description
						"Peak information rate: the rate at which tokens are added
						to the secondary bucket.";
				}

				leaf pbs {
					when "((current()/../mode = 'sr_tcm') or (current()/../mode = 'tr_tcm'))";
					must "((not(current()/../cbs)) or (current() >= current()/../cbs))" {
						error-message "pbs must be greater than or equal to cbs";
					}
					type uint64;
					description
						"Excess/peak burst size: the depth of the secondary token
						bucket.";
				}

				leaf green_action {
					type copp_packet_action;
					default "forward";
					description
						"Action for packets classified as green by the policer.";
				}

				leaf yellow_action {
					when "((current()/../mode = 'sr_tcm') or (current()/../mode = 'tr_tcm'))";
					type copp_packet_action;
					default "forward";
					description
						"Action for packets classified as yellow by the policer.";
				}

				leaf red_action {
					type copp_packet_action;
					default "forward";
					description
						"Action for packets classified as red by the policer.";
				}
			}
			/* end of list COPP_GROUP_LIST */
		}
		/* end of container COPP_GROUP */

		container COPP_TRAP {

			description
				"CoPP trap entries that bind trap IDs to CoPP groups.";

			list COPP_TRAP_LIST {

				description
					"A named CoPP trap binding trap IDs to a policing group.";
				key name;

				leaf name {
					type string;
					description "Control plane policing trap name.";
				}

				leaf trap_ids {
					type string;
					description
						"Comma-separated list of trap identifiers bound to this
						entry, for example \"bgp,bgpv6\".";
				}

				leaf trap_group {
					type leafref {
						path "/copp:sonic-copp/copp:COPP_GROUP/copp:COPP_GROUP_LIST/copp:name";
					}
					description
						"Reference to the CoPP group that polices these traps.";
				}

				leaf always_enabled {
					type boolean;
					description
						"When true, the trap is always installed regardless of
						feature enablement.";
				}
			}
			/* end of list COPP_TRAP_LIST */
		}
		/* end of container COPP_TRAP */
	}
	/* end of top level container */
}
