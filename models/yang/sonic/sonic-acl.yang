module sonic-acl {
	namespace "http://github.com/Azure/sonic-acl";
	prefix acl;
	yang-version 1.1;

	import ietf-inet-types {
		prefix inet;
	}

	import sonic-port {
		prefix prt;
	}

	import sonic-policer {
		prefix policer;
	}

	organization
		"SONiC";

	contact
		"SONiC";

	description
		"SONIC ACL";

	revision 2019-05-15 {
		description
			"Initial revision.";
	}

	container sonic-acl {

		container ACL_TABLE {

			list ACL_TABLE_LIST {
				key "aclname";

				leaf aclname {
					type string {
						pattern '[a-zA-Z0-9]{1}([-a-zA-Z0-9_]{1,63})' {
							error-app-tag aclname-invalid;
						}
					}
				}

				leaf policy_desc {
					type string {
						length 1..255 {
							error-app-tag policy-desc-invalid-length;
						}
					}
				}

				leaf oc_set_name {
					description
						"OpenConfig acl-set name as configured over gNMI. SONiC
						ACL_TABLE keys normalize spaces and dashes; this leaf
						preserves the client-visible set name for read-back.";
					type string {
						length 1..255 {
							error-app-tag oc-set-name-invalid-length;
						}
					}
				}

				leaf stage {
					type enumeration {
						enum INGRESS;
						enum EGRESS;
					}
				}

				leaf type {
					description
						"Type of the ACL table. The built-in types are
						enumerated; a table type defined in ACL_TABLE_TYPE is
						referenced by its name. The built-in types are matched
						first, so an ACL_TABLE_TYPE must not reuse one of those
						names.";
					type union {
						type enumeration {
							enum MIRROR;
							enum MIRRORV6;
							enum L3;
							enum L3V6;
							enum CTRLPLANE;
						}
						type string {
							pattern '[a-zA-Z0-9]{1}([-a-zA-Z0-9_]{1,63})' {
								error-app-tag acl-table-type-invalid;
							}
						}
					}
				}

				leaf-list services {
					description "Management services a control-plane (CTRLPLANE) ACL is applied to, e.g. SSH, SNMP, NTP, EXTERNAL_CLIENT.";
					type string;
				}

				leaf-list ports {
					type leafref {
						path "/prt:sonic-port/prt:PORT/prt:PORT_LIST/prt:ifname";
					}
				}
			}
		}

		container ACL_RULE {

			list ACL_RULE_LIST { 
				key "aclname rulename";

				leaf aclname {
					type leafref {
						path "../../../ACL_TABLE/ACL_TABLE_LIST/aclname";
					}
				} 

				leaf rulename {
					type string {
						pattern '[a-zA-Z0-9]{1}([-a-zA-Z0-9_]{1,63})' {
							error-app-tag rulename-invalid;
						}
					}
				}

				leaf PRIORITY {
					type uint16 {
						range "1..65535"{
							error-app-tag priority-invalid-range;
							error-message "Invalid ACL rule priority.";
						}
					}
				}

				leaf RULE_DESCRIPTION {
					type string {
						length 1..255 {
							error-app-tag ruledesc-invalid-length;
						}
					}
				}

				leaf PACKET_ACTION {
					mandatory true;
					type enumeration {
						enum FORWARD;
						enum ACCEPT;
						enum DROP;
						enum REDIRECT;
						enum DO_NOT_NAT;
						enum DISABLE_TRIM;
					}
				}

				leaf SET_TC {
					description
						"Traffic class (0..7) assigned to matching packets, realized as
						the aclorch SET_TC action (SAI_ACL_ENTRY_ATTR_ACTION_SET_TC).
						SET_TC is valid on an ingress L3/L3V6 table, or a custom
						table type that lists SET_TC among its ACTIONS. That guard
						is enforced by aclorch (parseAclTableTypeActions /
						validateAddAction reject SET_TC on a table that does not
						advertise it), so it is intentionally NOT expressed here as
						a cross-table 'must': CVL validates each table in a batch
						independently, and a rule carrying SET_TC is typically
						written in the same transaction that creates its
						ACL_TABLE/ACL_TABLE_TYPE, so a cross-table must would fire
						non-deterministically before the sibling tables are
						visible.";
					type uint8 {
						range 0..7 {
							error-app-tag set-tc-invalid-range;
						}
					}
				}

				leaf SET_DSCP {
					description
						"DSCP (0..63) rewritten on matching packets, realized as the
						aclorch SET_DSCP action (SAI_ACL_ENTRY_ATTR_ACTION_SET_DSCP).
						It is valid on an ingress table whose custom table type
						lists SET_DSCP among its ACTIONS; aclorch enforces that, for
						the reason given under SET_TC.";
					type uint8 {
						range 0..63 {
							error-app-tag set-dscp-invalid-range;
						}
					}
				}

				leaf IP_TYPE {
					mandatory true;
					type enumeration {
						enum ANY;
						enum IP;
						enum IPV4;
						enum IPV4ANY;
						enum NON_IPV4;
						enum IPV6ANY;
						enum NON_IPV6;
					}
				}

				leaf IP_PROTOCOL {
					type uint8 {
						range "1|2|6|17|46|47|51|58|103|115";
					}
				}

				leaf ETHER_TYPE {
					type string {
						pattern "(0x88CC)|(0x8100)|(0x8915)|(0x0806)|(0x0800)|(0x86DD)|(0x8847)" {
							error-message "Invalid ACL Rule Ether Type";
							error-app-tag ether-type-invalid;
						}
					}
				}

				leaf ICMP_TYPE {
					description "ICMPv4 type value to match";
					type uint8 {
						range "0..255";
					}
				}

				leaf ICMP_CODE {
					description "ICMPv4 code value to match";
					type uint8 {
						range "0..255";
					}
				}

				leaf ICMPV6_TYPE {
					description "ICMPv6 type value to match";
					type uint8 {
						range "0..255";
					}
				}

				leaf ICMPV6_CODE {
					description "ICMPv6 code value to match";
					type uint8 {
						range "0..255";
					}
				}

				choice ip_src_dst {
					case ipv4_src_dst {
						when "boolean(IP_TYPE[.='ANY' or .='IP' or .='IPV4' or .='IPV4ANY'])";
						leaf SRC_IP {
							type inet:ipv4-prefix;
						}
						leaf DST_IP {
							type inet:ipv4-prefix;
						}
					}
					case ipv6_src_dst {
						when "boolean(IP_TYPE[.='ANY' or .='IP' or .='IPV6' or .='IPV6ANY'])";
						leaf SRC_IPV6 {
							type inet:ipv6-prefix;    
						}
						leaf DST_IPV6 {
							type inet:ipv6-prefix;    
						}
					}
				}

				choice src_port {
					case l4_src_port {
						leaf L4_SRC_PORT {
							type inet:port-number;
						}
					}
					case l4_src_port_range {
						leaf L4_SRC_PORT_RANGE {
							type string {
								pattern "[0-9]{1,5}(-)[0-9]{1,5}" {
									error-app-tag src-port-range-invalid;
								}
							}
						}
					}
				}

				choice dst_port {
					case l4_dst_port {
						leaf L4_DST_PORT {
							type inet:port-number;
						}
					}
					case l4_dst_port_range {
						leaf L4_DST_PORT_RANGE {
							type string {
								pattern "[0-9]{1,5}(-)[0-9]{1,5}" {
									error-app-tag dst-port-range-invalid;
								}
							}
						}
					}
				}

				leaf TCP_FLAGS { 
					type string {
						pattern "0[xX][0-9a-fA-F]{2}[/]0[xX][0-9a-fA-F]{2}" {
							error-app-tag tcp-flag-invalid;
						}
					}
				}

				leaf DSCP { 
					description
						"DSCP to match, either one value or 'value/mask', which
						aclorch accepts as a masked match.";
					type union {
						type inet:dscp;
						type string {
							pattern "([0-9]|[1-5][0-9]|6[0-3])/([0-9]|[1-5][0-9]|6[0-3])" {
								error-app-tag dscp-mask-invalid;
							}
						}
					}
				}

				leaf POLICER_ACTION {
					description
						"Policer applied to traffic matching this rule. aclorch
						resolves the name to a policer OID and attaches it with
						SAI_ACL_ENTRY_ATTR_ACTION_SET_POLICER, so the policer
						has to exist before the rule is created.

						The table type must list POLICER_ACTION among its
						ACTIONS. The built-in L3 and L3V6 types allow only
						PACKET_ACTION and REDIRECT, so policing requires a
						custom ACL_TABLE_TYPE.";
					type leafref {
						path "/policer:sonic-policer/policer:POLICER/policer:POLICER_LIST/policer:name";
					}
				}
			}
		}

		container ACL_PORT_SET {

			description
				"Named L4 port sets that ACL rules match on, holding the
				CONFIG_DB form of the OpenConfig
				/defined-sets/port-sets/port-set list.

				An ACL_RULE carries a single L4 port match, so a set has to
				resolve to exactly one port or one contiguous range. The
				management layer resolves the set and writes the result to the
				referring rule's L4_SRC_PORT/L4_DST_PORT or
				L4_SRC_PORT_RANGE/L4_DST_PORT_RANGE field, so orchagent never
				reads this table.";

			list ACL_PORT_SET_LIST {
				key "name";

				leaf name {
					type string {
						pattern '[a-zA-Z0-9]{1}([-a-zA-Z0-9_]{1,63})' {
							error-app-tag port-set-name-invalid;
						}
					}
				}

				leaf DESCRIPTION {
					type string {
						length 1..255 {
							error-app-tag port-set-description-invalid-length;
						}
					}
				}

				leaf-list PORTS {
					description
						"Ports to match, each a single port or an inclusive
						range written as <lower>-<higher>.

						Only one entry is supported, because it has to fit in
						the single L4 port match of the referring ACL_RULE. The
						limit is not expressed as max-elements 1: CVL validates
						a leaf-list update against the merged view of the
						request and the current row, so replacing the single
						entry looks to it like a second one being added. The
						management layer, which owns this table, rejects a set
						holding more than one entry instead.";
					type string {
						pattern "[0-9]{1,5}(-[0-9]{1,5})?" {
							error-app-tag port-set-ports-invalid;
						}
					}
				}
			}
		}

		container ACL_RULE_PORT_SET {

			description
				"Port set references of ACL rules, one entry per rule that
				matches on a port set rather than on a literal port.

				The reference cannot be kept on the ACL_RULE itself: orchagent
				drops a rule outright when it carries a field it does not
				know. It is kept here so a read of the rule can report which
				set it matches, and so the rules referring to a set can be
				found and rewritten when the set changes. The management layer
				owns this table.";

			list ACL_RULE_PORT_SET_LIST {
				key "aclname rulename";

				leaf aclname {
					type string {
						pattern '[a-zA-Z0-9]{1}([-a-zA-Z0-9_]{1,63})' {
							error-app-tag aclname-invalid;
						}
					}
				}

				leaf rulename {
					type string {
						pattern '[a-zA-Z0-9]{1}([-a-zA-Z0-9_]{1,63})' {
							error-app-tag rulename-invalid;
						}
					}
				}

				leaf SRC_PORT_SET {
					description
						"Port set resolved into the rule's L4 source port
						match.";
					type leafref {
						path "../../../ACL_PORT_SET/ACL_PORT_SET_LIST/name";
					}
				}

				leaf DST_PORT_SET {
					description
						"Port set resolved into the rule's L4 destination port
						match.";
					type leafref {
						path "../../../ACL_PORT_SET/ACL_PORT_SET_LIST/name";
					}
				}
			}
		}

		container ACL_TABLE_TYPE {

			description
				"User-defined ACL table types. A table type declares which
				packet fields its tables may match and which actions their
				rules may carry, which is how matches and actions outside the
				built-in L3 and L3V6 sets are enabled.";

			list ACL_TABLE_TYPE_LIST {

				description "A custom ACL table type definition";
				key "ACL_TABLE_TYPE_NAME";

				leaf ACL_TABLE_TYPE_NAME {
					description
						"Name of the table type, referenced by ACL_TABLE:type.";
					type string {
						pattern '[a-zA-Z0-9]{1}([-a-zA-Z0-9_]{1,63})' {
							error-app-tag acl-table-type-name-invalid;
						}
					}
				}

				leaf-list MATCHES {
					description
						"Packet match fields tables of this type may use, named
						as the ACL_RULE fields are, e.g. SRC_IP, IP_PROTOCOL,
						L4_DST_PORT, TCP_FLAGS.";
					type string;
					ordered-by user;
					min-elements 1;
				}

				leaf-list ACTIONS {
					description
						"Actions rules of this type may carry, e.g.
						PACKET_ACTION, REDIRECT_ACTION, POLICER_ACTION.

						COUNTER must be included. aclorch creates a counter for
						every rule it adds, and the table is created with
						SAI_ACL_TABLE_ATTR_ACL_ACTION_TYPE_LIST built from this
						list, so omitting COUNTER makes the counter creation
						fail and takes the whole rule with it. The rule then
						sits in 'Pending creation' while the log reports
						'createCounter: Failed to create counter', which points
						at the counter rather than at the missing declaration.";
					type string;
					ordered-by user;
				}

				leaf-list BIND_POINTS {
					description
						"Bind point types a table of this type may attach to.";
					type enumeration {
						enum PORT;
						enum PORTCHANNEL;
					}
					ordered-by user;
					min-elements 1;
				}
			}
		}
	}
}
