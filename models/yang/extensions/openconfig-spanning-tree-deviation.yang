module openconfig-spanning-tree-deviation {

    yang-version "1.1";

    namespace "http://openconfig.net/yang/spanning-tree/deviation/extension";
    prefix "oc-stp-dev";

    import openconfig-extensions { prefix oc-ext; }
    import openconfig-spanning-tree { prefix oc-stp; }

    organization "Nokia";
    contact "Nokia";
    description
        "Deviation module for OpenConfig spanning-tree on SONiC.
         RSTP is supported via MSTP instance 0 (CIST).";

    oc-ext:openconfig-version "0.1.0";

    revision 2026-07-22 {
        description
            "Initial revision: RSTP-only support mapped to MSTI 0.";
        reference "0.1.0";
    }

    revision 2026-08-06 {
        description
            "Allow bridge-priority 0 on RSTP config to match SONiC/IEEE range.";
        reference "0.2.0";
    }

    revision 2026-08-22 {
        description
            "Allow RSTP interface port-priority 0 to match SONiC/IEEE range.";
        reference "0.2.1";
    }

    deviation /oc-stp:stp/oc-stp:mstp {
        deviate not-supported;
    }

    deviation /oc-stp:stp/oc-stp:rapid-pvst {
        deviate not-supported;
    }

    deviation /oc-stp:stp/oc-stp:rstp/oc-stp:config/oc-stp:bridge-priority {
        deviate replace {
            type uint32 {
                range "0..61440";
            }
        }
    }

    deviation /oc-stp:stp/oc-stp:rstp/oc-stp:interfaces/oc-stp:interface/oc-stp:config/oc-stp:port-priority {
        deviate replace {
            type uint8 {
                range "0..240";
            }
        }
    }

    deviation /oc-stp:stp/oc-stp:rstp/oc-stp:interfaces/oc-stp:interface/oc-stp:state/oc-stp:port-priority {
        deviate replace {
            type uint8 {
                range "0..240";
            }
        }
    }
}
