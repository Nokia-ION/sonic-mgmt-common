module openconfig-routing-policy-annot {

    yang-version "1";

    namespace "http://openconfig.net/yang/annotation/openconfig-routing-policy-annot";
    prefix "oc-rpol-annot";

    import sonic-extensions { prefix sonic-ext; }
    import openconfig-routing-policy { prefix oc-rpol; }
    import openconfig-bgp-policy { prefix oc-bgp-pol; }

    // Container-level dispatch entry point. The routing-policy lists have no
    // dedicated CONFIG_DB table of their own; policies live in
    // CONFIG_DB:ROUTE_MAP_SET and ROUTE_MAP. Marking them as virtual tables
    // keeps the translib parent-table existence check from rejecting a request
    // before the transformer runs, and binding the transformer here lets a
    // request anchored at routing-policy or any ancestor container be mapped
    // and populated in one pass.
    deviation /oc-rpol:routing-policy {
      deviate add {
          sonic-ext:virtual-table "true";
          sonic-ext:db-name "CONFIG_DB";
          sonic-ext:subtree-transformer "routing_policy_xfmr";
      }
    }

    // The lists themselves are bound to the container dispatch so that a
    // request for a whole list is answered from CONFIG_DB. Without it, translib
    // expands the list generically and reports one instance keyed by the
    // inherited parent key.
    deviation /oc-rpol:routing-policy/oc-rpol:policy-definitions/oc-rpol:policy-definition {
      deviate add {
          sonic-ext:virtual-table "true";
          sonic-ext:db-name "CONFIG_DB";
          sonic-ext:subtree-transformer "routing_policy_xfmr";
          sonic-ext:path-transformer "routing_policy_path_xfmr";
      }
    }

    deviation /oc-rpol:routing-policy/oc-rpol:policy-definitions/oc-rpol:policy-definition/oc-rpol:statements/oc-rpol:statement {
      deviate add {
          sonic-ext:virtual-table "true";
          sonic-ext:db-name "CONFIG_DB";
          sonic-ext:subtree-transformer "routing_policy_xfmr";
          sonic-ext:path-transformer "routing_policy_path_xfmr";
      }
    }

    deviation /oc-rpol:routing-policy/oc-rpol:defined-sets/oc-bgp-pol:bgp-defined-sets/oc-bgp-pol:community-sets/oc-bgp-pol:community-set {
      deviate add {
          sonic-ext:virtual-table "true";
          sonic-ext:db-name "CONFIG_DB";
          sonic-ext:subtree-transformer "routing_policy_xfmr";
      }
    }

    deviation /oc-rpol:routing-policy/oc-rpol:defined-sets/oc-bgp-pol:bgp-defined-sets/oc-bgp-pol:as-path-sets/oc-bgp-pol:as-path-set {
      deviate add {
          sonic-ext:virtual-table "true";
          sonic-ext:db-name "CONFIG_DB";
          sonic-ext:subtree-transformer "routing_policy_xfmr";
      }
    }

    deviation /oc-rpol:routing-policy/oc-rpol:policy-definitions/oc-rpol:policy-definition/oc-rpol:config {
      deviate add {
          sonic-ext:db-name "CONFIG_DB";
          sonic-ext:subtree-transformer "routing_policy_xfmr";
      }
    }

    deviation /oc-rpol:routing-policy/oc-rpol:policy-definitions/oc-rpol:policy-definition/oc-rpol:config/oc-rpol:name {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:name {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:config {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:config/oc-rpol:name {
      deviate add {
          sonic-ext:db-name "CONFIG_DB";
          sonic-ext:subtree-transformer "routing_policy_xfmr";
      }
    }

    deviation /oc-rpol:routing-policy/oc-rpol:defined-sets/oc-bgp-pol:bgp-defined-sets/oc-bgp-pol:community-sets/oc-bgp-pol:community-set/oc-bgp-pol:community-set-name {
      deviate add {
          sonic-ext:db-name "CONFIG_DB";
          sonic-ext:subtree-transformer "routing_policy_xfmr";
      }
    }

    deviation /oc-rpol:routing-policy/oc-rpol:defined-sets/oc-bgp-pol:bgp-defined-sets/oc-bgp-pol:community-sets/oc-bgp-pol:community-set/oc-bgp-pol:config {
      deviate add {
          sonic-ext:db-name "CONFIG_DB";
          sonic-ext:subtree-transformer "routing_policy_xfmr";
      }
    }

    deviation /oc-rpol:routing-policy/oc-rpol:defined-sets/oc-bgp-pol:bgp-defined-sets/oc-bgp-pol:community-sets/oc-bgp-pol:community-set/oc-bgp-pol:config/oc-bgp-pol:community-set-name {
      deviate add {
          sonic-ext:db-name "CONFIG_DB";
          sonic-ext:subtree-transformer "routing_policy_xfmr";
      }
    }

    deviation /oc-rpol:routing-policy/oc-rpol:defined-sets/oc-bgp-pol:bgp-defined-sets/oc-bgp-pol:community-sets/oc-bgp-pol:community-set/oc-bgp-pol:config/oc-bgp-pol:community-member {
      deviate add {
          sonic-ext:db-name "CONFIG_DB";
          sonic-ext:subtree-transformer "routing_policy_xfmr";
      }
    }

    deviation /oc-rpol:routing-policy/oc-rpol:defined-sets/oc-bgp-pol:bgp-defined-sets/oc-bgp-pol:community-sets/oc-bgp-pol:community-set/oc-bgp-pol:config/oc-bgp-pol:match-set-options {
      deviate add {
          sonic-ext:db-name "CONFIG_DB";
          sonic-ext:subtree-transformer "routing_policy_xfmr";
      }
    }

    deviation /oc-rpol:routing-policy/oc-rpol:defined-sets/oc-bgp-pol:bgp-defined-sets/oc-bgp-pol:ext-community-sets/oc-bgp-pol:ext-community-set {
      deviate add {
          sonic-ext:virtual-table "true";
          sonic-ext:db-name "CONFIG_DB";
          sonic-ext:subtree-transformer "routing_policy_xfmr";
      }
    }

    deviation /oc-rpol:routing-policy/oc-rpol:defined-sets/oc-bgp-pol:bgp-defined-sets/oc-bgp-pol:ext-community-sets/oc-bgp-pol:ext-community-set/oc-bgp-pol:ext-community-set-name {
      deviate add {
          sonic-ext:db-name "CONFIG_DB";
          sonic-ext:subtree-transformer "routing_policy_xfmr";
      }
    }

    deviation /oc-rpol:routing-policy/oc-rpol:defined-sets/oc-bgp-pol:bgp-defined-sets/oc-bgp-pol:ext-community-sets/oc-bgp-pol:ext-community-set/oc-bgp-pol:config {
      deviate add {
          sonic-ext:db-name "CONFIG_DB";
          sonic-ext:subtree-transformer "routing_policy_xfmr";
      }
    }

    deviation /oc-rpol:routing-policy/oc-rpol:defined-sets/oc-bgp-pol:bgp-defined-sets/oc-bgp-pol:ext-community-sets/oc-bgp-pol:ext-community-set/oc-bgp-pol:config/oc-bgp-pol:ext-community-set-name {
      deviate add {
          sonic-ext:db-name "CONFIG_DB";
          sonic-ext:subtree-transformer "routing_policy_xfmr";
      }
    }

    deviation /oc-rpol:routing-policy/oc-rpol:defined-sets/oc-bgp-pol:bgp-defined-sets/oc-bgp-pol:ext-community-sets/oc-bgp-pol:ext-community-set/oc-bgp-pol:config/oc-bgp-pol:ext-community-member {
      deviate add {
          sonic-ext:db-name "CONFIG_DB";
          sonic-ext:subtree-transformer "routing_policy_xfmr";
      }
    }

    deviation /oc-rpol:routing-policy/oc-rpol:defined-sets/oc-bgp-pol:bgp-defined-sets/oc-bgp-pol:ext-community-sets/oc-bgp-pol:ext-community-set/oc-bgp-pol:config/oc-bgp-pol:match-set-options {
      deviate add {
          sonic-ext:db-name "CONFIG_DB";
          sonic-ext:subtree-transformer "routing_policy_xfmr";
      }
    }

    // The prefix-set lists live in CONFIG_DB:PREFIX_SET and PREFIX. Both are
    // marked virtual so that the transformer answers a request for a whole
    // list, and the prefix list is keyed by ip-prefix and masklength-range
    // together while PREFIX also carries a sequence number in its key that
    // OpenConfig has no leaf for.
    deviation /oc-rpol:routing-policy/oc-rpol:defined-sets/oc-rpol:prefix-sets/oc-rpol:prefix-set {
      deviate add {
          sonic-ext:virtual-table "true";
          sonic-ext:db-name "CONFIG_DB";
          sonic-ext:subtree-transformer "routing_policy_xfmr";
      }
    }

    deviation /oc-rpol:routing-policy/oc-rpol:defined-sets/oc-rpol:prefix-sets/oc-rpol:prefix-set/oc-rpol:name {
      deviate add {
          sonic-ext:db-name "CONFIG_DB";
          sonic-ext:subtree-transformer "routing_policy_xfmr";
      }
    }

    deviation /oc-rpol:routing-policy/oc-rpol:defined-sets/oc-rpol:prefix-sets/oc-rpol:prefix-set/oc-rpol:config {
      deviate add {
          sonic-ext:db-name "CONFIG_DB";
          sonic-ext:subtree-transformer "routing_policy_xfmr";
      }
    }

    deviation /oc-rpol:routing-policy/oc-rpol:defined-sets/oc-rpol:prefix-sets/oc-rpol:prefix-set/oc-rpol:config/oc-rpol:name {
      deviate add {
          sonic-ext:db-name "CONFIG_DB";
          sonic-ext:subtree-transformer "routing_policy_xfmr";
      }
    }

    deviation /oc-rpol:routing-policy/oc-rpol:defined-sets/oc-rpol:prefix-sets/oc-rpol:prefix-set/oc-rpol:config/oc-rpol:mode {
      deviate add {
          sonic-ext:db-name "CONFIG_DB";
          sonic-ext:subtree-transformer "routing_policy_xfmr";
      }
    }

    deviation /oc-rpol:routing-policy/oc-rpol:defined-sets/oc-rpol:prefix-sets/oc-rpol:prefix-set/oc-rpol:prefixes/oc-rpol:prefix {
      deviate add {
          sonic-ext:virtual-table "true";
          sonic-ext:db-name "CONFIG_DB";
          sonic-ext:subtree-transformer "routing_policy_xfmr";
      }
    }

    deviation /oc-rpol:routing-policy/oc-rpol:defined-sets/oc-rpol:prefix-sets/oc-rpol:prefix-set/oc-rpol:prefixes/oc-rpol:prefix/oc-rpol:ip-prefix {
      deviate add {
          sonic-ext:db-name "CONFIG_DB";
          sonic-ext:subtree-transformer "routing_policy_xfmr";
      }
    }

    deviation /oc-rpol:routing-policy/oc-rpol:defined-sets/oc-rpol:prefix-sets/oc-rpol:prefix-set/oc-rpol:prefixes/oc-rpol:prefix/oc-rpol:masklength-range {
      deviate add {
          sonic-ext:db-name "CONFIG_DB";
          sonic-ext:subtree-transformer "routing_policy_xfmr";
      }
    }

    deviation /oc-rpol:routing-policy/oc-rpol:defined-sets/oc-rpol:prefix-sets/oc-rpol:prefix-set/oc-rpol:prefixes/oc-rpol:prefix/oc-rpol:config {
      deviate add {
          sonic-ext:db-name "CONFIG_DB";
          sonic-ext:subtree-transformer "routing_policy_xfmr";
      }
    }

    deviation /oc-rpol:routing-policy/oc-rpol:defined-sets/oc-rpol:prefix-sets/oc-rpol:prefix-set/oc-rpol:prefixes/oc-rpol:prefix/oc-rpol:config/oc-rpol:ip-prefix {
      deviate add {
          sonic-ext:db-name "CONFIG_DB";
          sonic-ext:subtree-transformer "routing_policy_xfmr";
      }
    }

    deviation /oc-rpol:routing-policy/oc-rpol:defined-sets/oc-rpol:prefix-sets/oc-rpol:prefix-set/oc-rpol:prefixes/oc-rpol:prefix/oc-rpol:config/oc-rpol:masklength-range {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-rpol:config {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-rpol:config/oc-rpol:policy-result {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-rpol:state {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-rpol:state/oc-rpol:policy-result {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:conditions/oc-rpol:match-prefix-set/oc-rpol:state {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:conditions/oc-rpol:match-prefix-set/oc-rpol:state/oc-rpol:prefix-set {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:conditions/oc-rpol:match-prefix-set/oc-rpol:state/oc-rpol:match-set-options {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:conditions/oc-rpol:match-prefix-set/oc-rpol:config {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:conditions/oc-rpol:match-prefix-set/oc-rpol:config/oc-rpol:prefix-set {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:conditions/oc-rpol:match-prefix-set/oc-rpol:config/oc-rpol:match-set-options {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-community {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-community/oc-bgp-pol:inline/oc-bgp-pol:state {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-community/oc-bgp-pol:inline/oc-bgp-pol:state/oc-bgp-pol:communities {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-community/oc-bgp-pol:inline/oc-bgp-pol:config {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-community/oc-bgp-pol:inline/oc-bgp-pol:config/oc-bgp-pol:communities {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-community/oc-bgp-pol:reference/oc-bgp-pol:state {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-community/oc-bgp-pol:reference/oc-bgp-pol:state/oc-bgp-pol:community-set-ref {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-community/oc-bgp-pol:reference/oc-bgp-pol:state/oc-bgp-pol:community-set-refs {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-community/oc-bgp-pol:reference/oc-bgp-pol:config {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-community/oc-bgp-pol:reference/oc-bgp-pol:config/oc-bgp-pol:community-set-refs {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-community/oc-bgp-pol:reference/oc-bgp-pol:config/oc-bgp-pol:community-set-ref {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-as-path-prepend/oc-bgp-pol:state {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-as-path-prepend/oc-bgp-pol:state/oc-bgp-pol:asn {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-as-path-prepend/oc-bgp-pol:state/oc-bgp-pol:repeat-n {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-as-path-prepend/oc-bgp-pol:config {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-as-path-prepend/oc-bgp-pol:config/oc-bgp-pol:asn {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:set-as-path-prepend/oc-bgp-pol:config/oc-bgp-pol:repeat-n {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:state {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:state/oc-bgp-pol:set-next-hop {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:state/oc-bgp-pol:set-route-origin {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:state/oc-bgp-pol:set-local-pref {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:state/oc-bgp-pol:set-med {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:state/oc-bgp-pol:set-med-action {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:config {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:config/oc-bgp-pol:set-next-hop {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:config/oc-bgp-pol:set-route-origin {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:config/oc-bgp-pol:set-local-pref {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:config/oc-bgp-pol:set-med {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:actions/oc-bgp-pol:bgp-actions/oc-bgp-pol:config/oc-bgp-pol:set-med-action {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:conditions/oc-bgp-pol:bgp-conditions/oc-bgp-pol:state {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:conditions/oc-bgp-pol:bgp-conditions/oc-bgp-pol:state/oc-bgp-pol:community-set {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:conditions/oc-bgp-pol:bgp-conditions/oc-bgp-pol:state/oc-bgp-pol:ext-community-set {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:conditions/oc-bgp-pol:bgp-conditions/oc-bgp-pol:state/oc-bgp-pol:local-pref-eq {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:conditions/oc-bgp-pol:bgp-conditions/oc-bgp-pol:state/oc-bgp-pol:med-eq {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:conditions/oc-bgp-pol:bgp-conditions/oc-bgp-pol:state/oc-bgp-pol:origin-eq {
      deviate add {
          sonic-ext:db-name "STATE_DB";
          sonic-ext:subtree-transformer "routing_policy_xfmr";
      }
    }

    deviation /oc-rpol:routing-policy/oc-rpol:policy-definitions/oc-rpol:policy-definition/oc-rpol:statements/oc-rpol:statement/oc-rpol:conditions/oc-bgp-pol:bgp-conditions/oc-bgp-pol:config {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:conditions/oc-bgp-pol:bgp-conditions/oc-bgp-pol:config/oc-bgp-pol:med-eq {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:conditions/oc-bgp-pol:bgp-conditions/oc-bgp-pol:config/oc-bgp-pol:origin-eq {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:conditions/oc-bgp-pol:bgp-conditions/oc-bgp-pol:config/oc-bgp-pol:local-pref-eq {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:conditions/oc-bgp-pol:bgp-conditions/oc-bgp-pol:config/oc-bgp-pol:community-set {
      deviate add {
          sonic-ext:db-name "CONFIG_DB";
          sonic-ext:subtree-transformer "routing_policy_xfmr";
      }
    }

    deviation /oc-rpol:routing-policy/oc-rpol:policy-definitions/oc-rpol:policy-definition/oc-rpol:statements/oc-rpol:statement/oc-rpol:conditions/oc-bgp-pol:bgp-conditions/oc-bgp-pol:config/oc-bgp-pol:ext-community-set {
      deviate add {
          sonic-ext:db-name "CONFIG_DB";
          sonic-ext:subtree-transformer "routing_policy_xfmr";
      }
    }

}
