module openconfig-system-annot {

    yang-version "1";

    namespace "http://openconfig.net/yang/openconfig-system-annot";
    prefix "oc-sys-annot";

    import openconfig-system { prefix oc-sys; }
    import openconfig-system-logging { prefix oc-log; }
    import openconfig-system-logging-ext { prefix oc-log-ext; }
    import openconfig-system-ext { prefix oc-sys-ext; }
    import sonic-extensions {prefix sonic-ext; }
    import openconfig-system-grpc { prefix oc-sys-grpc; }
    import gnsi-pathz { prefix gnsi-pathz; }
    import gnsi-credentialz { prefix gnsi-credz; }
    import openconfig-gnsi-credentialz { prefix oc-gnsi-credz; }
    import openconfig-system-controlplane { prefix oc-sys-copp; }
    import sonic-system-controlplane-ext { prefix sonic-sys-cp-ext; }

    deviation /oc-sys:system/oc-sys:ssh-server/oc-sys:state {
      deviate add {
        sonic-ext:db-name "STATE_DB";
        sonic-ext:subtree-transformer "ssh_server_state_xfmr";
      }
    }

    deviation /oc-sys:system/oc-sys:ssh-server/oc-sys:config {
      deviate add {
        sonic-ext:subtree-transformer "ssh_server_config_xfmr";
      }
    }

    deviation /oc-sys:system/gnsi-credz:console/gnsi-credz:config {
      deviate add {
        sonic-ext:subtree-transformer "serial_console_xfmr";
      }
    }

    deviation /oc-sys:system/oc-sys:aaa/oc-sys:authentication/oc-sys:glome/oc-sys:state {
      deviate add {
        sonic-ext:db-name "STATE_DB";
        sonic-ext:table-name "CREDENTIALS";
        sonic-ext:key-name "GLOME_CONFIG";
      }
    }

    deviation /oc-sys:system/oc-sys:aaa/oc-sys:authentication/oc-sys:glome/oc-sys:state/oc-gnsi-credz:active-glome-key-version {
      deviate add {
        sonic-ext:field-name "key_version";
      }
    }

    deviation /oc-sys:system/oc-sys:aaa/oc-sys:authentication/oc-sys:glome/oc-sys:state/oc-gnsi-credz:active-glome-key-created-on {
      deviate add {
        sonic-ext:field-name "last_updated";
      }
    }

    deviation /oc-sys:system/oc-sys:aaa/oc-sys:authentication/oc-sys:glome/oc-sys:state/oc-gnsi-credz:enabled {
      deviate add {
        sonic-ext:field-name "enabled";
      }
    }

    deviation /oc-sys:system/oc-gnsi-credz:console {
      deviate add {
        sonic-ext:db-name "STATE_DB";
        sonic-ext:subtree-transformer "console_counters_xfmr";
      }
    }

    deviation /oc-sys:system/oc-sys-grpc:grpc-servers {
        deviate add {
            sonic-ext:key-transformer "grpc_server_key_xfmr";
            sonic-ext:subtree-transformer "grpc_server_xfmr";
        }
    }

    /* Sits on the list rather than the container above it, so that a
       subscription wildcarding the server name has its key resolved. */
    deviation /oc-sys:system/oc-sys-grpc:grpc-servers/oc-sys-grpc:grpc-server {
        deviate add {
            sonic-ext:path-transformer "grpc_server_path_xfmr";
        }
    }

    deviation /oc-sys:system/oc-sys:config {
        deviate add {
            sonic-ext:key-transformer "sys_config_key_xfmr";
            sonic-ext:table-name "DEVICE_METADATA";
            sonic-ext:subtree-transformer "sys_config_xfmr";
        }
    }

    deviation /oc-sys:system/oc-sys:state {
        deviate add {
            sonic-ext:subtree-transformer "sys_state_xfmr";
        }
    }

    deviation /oc-sys:system/oc-sys:aaa/oc-sys:authorization/oc-sys:state {
      deviate add {
        sonic-ext:db-name "STATE_DB";
        sonic-ext:subtree-transformer "authz_policy_xfmr";
      }
    }

    deviation /oc-sys:system/gnsi-pathz:gnmi-pathz-policies {
      deviate add {
        sonic-ext:key-transformer "pathz_policies_key_xfmr";
        sonic-ext:subtree-transformer "pathz_policies_xfmr";
      }
    }

    deviation /oc-sys:system/oc-sys:memory {
        deviate add {
            sonic-ext:subtree-transformer "sys_memory_xfmr";
            sonic-ext:db-name "STATE_DB";
            sonic-ext:table-name "MEMORY_STATS";
            sonic-ext:key-name "system";
        }
    }

    deviation /oc-sys:system/oc-sys:cpus/oc-sys:cpu {
        deviate add {
            sonic-ext:subtree-transformer "sys_cpus_xfmr";
            sonic-ext:db-name "STATE_DB";
            sonic-ext:table-name "CPU_STATS";
        }
    }

    deviation /oc-sys:system/oc-sys:processes/oc-sys:process {
        deviate add {
            sonic-ext:subtree-transformer "sys_procs_xfmr";
            sonic-ext:db-name "STATE_DB";
            sonic-ext:table-name "PROCESS_STATS";
        }
    }

    deviation /oc-sys:system/oc-sys:ntp/oc-sys:state/oc-sys:enabled {
        deviate add {
            sonic-ext:field-name "ntp_enabled";
        }
    }

    deviation /oc-sys:system/oc-sys:ntp/oc-sys:state/oc-sys:auth-mismatch {
        deviate not-supported;
    }

    deviation /oc-sys:system/oc-sys:ntp/oc-sys:state/oc-sys:enable-ntp-auth {
        deviate add {
            sonic-ext:field-name "auth_enabled";
        }
    }

    /* NTP global config (source-interface, openconfig-system-ext) is handled by
       a subtree transformer that maps to NTP|global. */
    deviation /oc-sys:system/oc-sys:ntp/oc-sys:config {
        deviate add {
            sonic-ext:subtree-transformer "ntp_config_xfmr";
        }
    }

    /* NTP operational-state source-interface mirrors the config value. Bind the
       state container to NTP|global explicitly (the base oc-system state leaves
       have no working SONiC mapping on this platform) so source-interface is
       returned on GET from the same src_intf field the config path writes. */
    deviation /oc-sys:system/oc-sys:ntp/oc-sys:state {
        deviate add {
            sonic-ext:table-name "NTP";
            sonic-ext:key-name "global";
        }
    }

    deviation /oc-sys:system/oc-sys:ntp/oc-sys:state/oc-sys-ext:source-interface {
        deviate add {
            sonic-ext:field-name "src_intf";
        }
    }

    deviation /oc-sys:system/oc-sys:ntp/oc-sys:servers {
        deviate add {
            sonic-ext:subtree-transformer "ntp_servers_list_xfmr";
        }
    }

    deviation /oc-sys:system/oc-sys:dns/oc-sys:servers {
        deviate add {
            sonic-ext:subtree-transformer "dns_servers_list_xfmr";
        }
    }

    deviation /oc-sys:system/oc-sys:dns/oc-sys:config {
        deviate add {
            sonic-ext:subtree-transformer "dns_config_xfmr";
        }
    }

    deviation /oc-sys:system/oc-sys:dns/oc-sys:state {
        deviate add {
            sonic-ext:subtree-transformer "dns_state_xfmr";
        }
    }

    deviation /oc-sys:system/oc-sys:aaa/oc-sys:server-groups {
        deviate add {
            sonic-ext:subtree-transformer "tacacs_server_groups_xfmr";
        }
    }

    deviation /oc-sys:system/oc-sys:aaa/oc-sys:authentication {
        deviate add {
            sonic-ext:subtree-transformer "aaa_authentication_xfmr";
        }
    }

    deviation /oc-sys:system/oc-log:logging/oc-log:remote-servers {
      deviate add {
        sonic-ext:subtree-transformer "remote_servers_list_xfmr";
      }
    }

    deviation /oc-sys:system/oc-log:logging/oc-log:remote-servers/oc-log:remote-server {
      deviate add {
        sonic-ext:db-name "CONFIG_DB";
        sonic-ext:table-name "SYSLOG_SERVER";
        sonic-ext:path-transformer "remote_server_path_xfmr";
      }
    }

    deviation /oc-sys:system/oc-log:logging/oc-log:remote-servers/oc-log:remote-server/oc-log:config {
      deviate add {
          sonic-ext:db-name "CONFIG_DB";
      }
    }

    deviation /oc-sys:system/oc-log:logging/oc-log:remote-servers/oc-log:remote-server/oc-log:config/oc-log:remote-port {
      deviate add {
        sonic-ext:field-name "port";
      }
    }

    deviation /oc-sys:system/oc-log:logging/oc-log:remote-servers/oc-log:remote-server/oc-log:config/oc-log:source-address {
      deviate add {
        sonic-ext:field-name "source";
      }
    }

    deviation /oc-sys:system/oc-log:logging/oc-log:remote-servers/oc-log:remote-server/oc-log:config/oc-log:network-instance {
      deviate add {
        sonic-ext:field-name "vrf";
      }
    }

    deviation /oc-sys:system/oc-log:logging/oc-log:remote-servers/oc-log:remote-server/oc-log:state/oc-log:remote-port {
      deviate add {
        sonic-ext:field-name "port";
      }
    }

    deviation /oc-sys:system/oc-log:logging/oc-log:remote-servers/oc-log:remote-server/oc-log:state/oc-log:source-address {
      deviate add {
        sonic-ext:field-name "source";
      }
    }

    deviation /oc-sys:system/oc-log:logging/oc-log:remote-servers/oc-log:remote-server/oc-log:state/oc-log:network-instance {
      deviate add {
        sonic-ext:field-name "vrf";
      }
    }

    deviation /oc-sys:system/oc-log:logging/oc-log:remote-servers/oc-log:remote-server/oc-log:config/oc-log:transport-security {
      deviate add {
        sonic-ext:field-name "transport_security";
      }
    }

    deviation /oc-sys:system/oc-log:logging/oc-log:remote-servers/oc-log:remote-server/oc-log:state/oc-log:transport-security {
      deviate add {
        sonic-ext:field-name "transport_security";
      }
    }

    deviation /oc-sys:system/oc-log:logging/oc-log:remote-servers/oc-log:remote-server/oc-log:config/oc-log:tls-profile-id {
      deviate add {
        sonic-ext:field-name "tls_profile_id";
      }
    }

    deviation /oc-sys:system/oc-log:logging/oc-log:remote-servers/oc-log:remote-server/oc-log:state/oc-log:tls-profile-id {
      deviate add {
        sonic-ext:field-name "tls_profile_id";
      }
    }

    deviation /oc-sys:system/oc-log:logging/oc-log:remote-servers/oc-log:remote-server/oc-log:config/oc-log-ext:tls-permitted-peers {
      deviate add {
        sonic-ext:field-name "tls_permitted_peers";
      }
    }

    deviation /oc-sys:system/oc-log:logging/oc-log:remote-servers/oc-log:remote-server/oc-log:state/oc-log-ext:tls-permitted-peers {
      deviate add {
        sonic-ext:field-name "tls_permitted_peers";
      }
    }

    deviation /oc-sys:system/oc-log:logging/oc-log:remote-servers/oc-log:remote-server/oc-log:state/oc-log:host {
      deviate add {
          sonic-ext:field-transformer "syslog_server_ip_fld_xfmr";
      }
    }

    deviation /oc-sys:system/oc-log:logging/oc-log:remote-servers/oc-log:remote-server/oc-log:selectors {
      deviate add {
        sonic-ext:table-name "NONE";
        sonic-ext:subtree-transformer "remote_servers_list_xfmr";
      }
    }

    deviation /oc-sys:system/oc-log:logging/oc-log:remote-servers/oc-log:remote-server/oc-log:selectors/oc-log:selector {
      deviate add {
        sonic-ext:subtree-transformer "remote_servers_list_xfmr";
        sonic-ext:key-transformer "syslog_selector_key_xfmr";
      }
    }

    deviation /oc-sys:system/oc-log:logging/oc-log:remote-servers/oc-log:remote-server/oc-log:selectors/oc-log:selector/oc-log:config/oc-log:severity {
      deviate add {
        sonic-ext:field-transformer "syslog_selector_severity_fld_xfmr";
      }
    }

    deviation /oc-sys:system/oc-log:logging/oc-log:remote-servers/oc-log:remote-server/oc-log:selectors/oc-log:selector/oc-log:config/oc-log:facility {
      deviate add {
        sonic-ext:field-transformer "syslog_selector_facility_fld_xfmr";
      }
    }

    /* Global logging source-interface (openconfig-system-ext) is handled by a
       subtree transformer that maps to SYSLOG_CONFIG|GLOBAL:src_intf. */
    deviation /oc-sys:system/oc-log:logging/oc-sys-ext:config {
      deviate add {
        sonic-ext:subtree-transformer "logging_config_xfmr";
      }
    }

    /* Global logging operational-state extensions live in a dedicated ext
       container with no base-model backing, so bind it to SYSLOG_CONFIG|GLOBAL
       explicitly. source-interface then mirrors the configured src_intf. */
    deviation /oc-sys:system/oc-log:logging/oc-sys-ext:state {
      deviate add {
        sonic-ext:table-name "SYSLOG_CONFIG";
        sonic-ext:key-name "GLOBAL";
      }
    }

    deviation /oc-sys:system/oc-log:logging/oc-sys-ext:state/oc-sys-ext:source-interface {
      deviate add {
        sonic-ext:field-name "src_intf";
      }
    }

    /* Core file cleanup (openconfig-system-ext) maps to AUTO_TECHSUPPORT|GLOBAL.
       Config and state are handled together because state/enabled is derived
       from the 'state' field rather than mirroring a config leaf. */
    deviation /oc-sys:system/oc-sys-ext:core-file-cleanup {
      deviate add {
        sonic-ext:subtree-transformer "core_file_cleanup_xfmr";
      }
    }

    /* Tech-support dump cleanup (openconfig-system-ext) maps to the same
       AUTO_TECHSUPPORT|GLOBAL row, handled the same way as core-file-cleanup. */
    deviation /oc-sys:system/oc-sys-ext:tech-support-cleanup {
      deviate add {
        sonic-ext:subtree-transformer "tech_support_cleanup_xfmr";
      }
    }

    /*
     * Control-plane traffic filtering in hardware.
     *
     * A control-plane ACL set is the same object as the ACL set of the same
     * name and type in the OpenConfig ACL model, so it maps to the same
     * CONFIG_DB ACL_TABLE entry that /openconfig-acl:acl creates. Binding an
     * ACL set to the control plane therefore does not create a new table; it
     * adds the 'stage' and 'ports' fields that make aclorch program the
     * already-configured rules into the ASIC.
     *
     * The ACL_TABLE key is composed the same way acl_app.go composes it
     * (getAclKeyStrFromOCKey): the set name with spaces and hyphens replaced
     * by underscores, an underscore, then the OpenConfig type name, for
     * example restrict_mgmt_ACL_IPV4. Both producers must agree on the key or
     * the binding lands on a different row than the rules.
     *
     * These deviations belong in this file rather than alongside the
     * control-plane model because annotToDbMapBuild derives the module
     * prefix of the annotated xpath from the annotation file name, so an
     * annotation of a node under /oc-sys:system is only applied when it is
     * declared in openconfig-system-annot.
     */

    /*
     * The whole acl-set list is handled by one subtree transformer rather than
     * by per-leaf mappings.
     *
     * ACL_TABLE holds the stage and the ports of a binding in the same entry
     * that /openconfig-acl:acl owns, and its 'ports' field is shared with the
     * /openconfig-acl:acl/interfaces bindings. Withdrawing a control-plane
     * binding therefore has to remove only the ports that binding contributed
     * and may drop the stage only once none are left. Per-leaf mappings decide
     * those two fields independently and in an unspecified order, and a
     * field-name mapping of bind-interfaces onto 'ports' let a delete of the
     * list instance clear the field outright, unbinding interfaces the ACL
     * model had bound. Deciding both in one place is what makes the
     * withdrawal correct.
     */
    deviation /oc-sys:system/oc-sys-copp:control-plane-traffic/oc-sys-copp:ingress/oc-sys-copp:acl/oc-sys-copp:acl-set {
      deviate add {
        sonic-ext:subtree-transformer "cp_acl_xfmr";
      }
    }
}
