module sonic-show-techsupport-annot {

    yang-version "1";

    namespace "http://openconfig.net/Azure/sonic-show-techsupport-annot";
    prefix "show-techsupport-annot";

    import sonic-extensions { prefix sonic-ext; }
    import sonic-show-techsupport { prefix sshwtchspt; }

    deviation /sshwtchspt:sonic-show-techsupport-info {
      deviate add {
        sonic-ext:rpc-callback "rpc_showtech_cb";
      }
    }

}
