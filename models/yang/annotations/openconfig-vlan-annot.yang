module openconfig-vlan-annot {

    yang-version "1";

    namespace "http://openconfig.net/yang/annotation/oc-vlan-annot";
    prefix "oc-vlan-annot";

    import sonic-extensions { prefix sonic-ext; }
    import openconfig-vlan { prefix oc-vlan; }

    organization
        "SONiC";

    contact
        "SONiC";

    description
        "OpenConfig VLAN YANG annotations for SONiC transformer framework.";

    revision 2026-08-21 {
        description
            "Add subtree SET of the VLAN catalog.";
    }

    revision 2026-08-18 {
        description
            "Add subtree GET of the VLAN catalog.";
    }

    deviation /oc-vlan:vlans {
        deviate add {
            sonic-ext:db-name "CONFIG_DB";
            sonic-ext:subtree-transformer "oc_vlans_xfmr";
        }
    }
}
