module openconfig-network-instance-annot {

    yang-version "1";

    namespace "http://openconfig.net/yang/annotation/openconfig-network-instance-annot";
    prefix "oc-netinst-annot";

    import sonic-extensions { prefix sonic-ext; }
    import openconfig-network-instance { prefix oc-netinst; }

    // The network-instance and protocol OC lists have no dedicated CONFIG_DB
    // table; BGP global config is stored in CONFIG_DB:BGP_GLOBALS|<ni-name>.
    // Mark these ancestor lists as virtual tables so the translib parent-table
    // existence check (verifyParentTableOc) does not reject the request before
    // the BGP global config transformer runs.
    //
    // The three levels enclosing every mapped subtree are bound to a dispatch
    // of their own. A GET there answers with everything this module maps under
    // a network instance, and a SET or a DELETE is refused, neither having one
    // meaning at a level owned by four transformers. Every descendant that
    // maps something carries its own deviation, and translib gives the nearest
    // one precedence, so this binding does not claim them.
    deviation /oc-netinst:network-instances {
      deviate add {
          sonic-ext:virtual-table "true";
          sonic-ext:db-name "CONFIG_DB";
          sonic-ext:subtree-transformer "ni_container_xfmr";
      }
    }

    deviation /oc-netinst:network-instances/oc-netinst:network-instance {
      deviate add {
          sonic-ext:virtual-table "true";
          sonic-ext:db-name "CONFIG_DB";
          sonic-ext:subtree-transformer "ni_container_xfmr";
      }
    }

    deviation /oc-netinst:network-instances/oc-netinst:network-instance/oc-netinst:config {
      deviate add {
          sonic-ext:virtual-table "true";
          sonic-ext:db-name "CONFIG_DB";
          sonic-ext:subtree-transformer "ni_container_xfmr";
      }
    }

    deviation /oc-netinst:network-instances/oc-netinst:network-instance/oc-netinst:config/oc-netinst:name {
      deviate add {
          sonic-ext:virtual-table "true";
          sonic-ext:db-name "CONFIG_DB";
          sonic-ext:subtree-transformer "ni_container_xfmr";
      }
    }

    deviation /oc-netinst:network-instances/oc-netinst:network-instance/oc-netinst:config/oc-netinst:type {
      deviate add {
          sonic-ext:virtual-table "true";
          sonic-ext:db-name "CONFIG_DB";
          sonic-ext:subtree-transformer "ni_container_xfmr";
      }
    }

    deviation /oc-netinst:network-instances/oc-netinst:network-instance/oc-netinst:state {
      deviate add {
          sonic-ext:virtual-table "true";
          sonic-ext:db-name "CONFIG_DB";
          sonic-ext:subtree-transformer "ni_container_xfmr";
      }
    }

    deviation /oc-netinst:network-instances/oc-netinst:network-instance/oc-netinst:state/oc-netinst:name {
      deviate add {
          sonic-ext:virtual-table "true";
          sonic-ext:db-name "CONFIG_DB";
          sonic-ext:subtree-transformer "ni_container_xfmr";
      }
    }

    deviation /oc-netinst:network-instances/oc-netinst:network-instance/oc-netinst:state/oc-netinst:type {
      deviate add {
          sonic-ext:virtual-table "true";
          sonic-ext:db-name "CONFIG_DB";
          sonic-ext:subtree-transformer "ni_container_xfmr";
      }
    }

    deviation /oc-netinst:network-instances/oc-netinst:network-instance/oc-netinst:protocols {
      deviate add {
          sonic-ext:virtual-table "true";
          sonic-ext:db-name "CONFIG_DB";
          sonic-ext:subtree-transformer "ni_container_xfmr";
      }
    }

    deviation /oc-netinst:network-instances/oc-netinst:network-instance/oc-netinst:protocols/oc-netinst:protocol {
      deviate add {
          sonic-ext:virtual-table "true";
          sonic-ext:db-name "CONFIG_DB";
          sonic-ext:subtree-transformer "ni_bgp_global_cfg_xfmr";
      }
    }

    // Container-level BGP dispatch entry point.
    deviation /oc-netinst:network-instances/oc-netinst:network-instance/oc-netinst:protocols/oc-netinst:protocol/oc-netinst:bgp {
      deviate add {
          sonic-ext:virtual-table "true";
          sonic-ext:db-name "CONFIG_DB";
          sonic-ext:subtree-transformer "ni_bgp_global_cfg_xfmr";
      }
    }

    // The list itself is bound to the container dispatch so that a request for
    // the whole list is answered from CONFIG_DB. Without it, translib expands
    // the list generically and reports one instance keyed by the inherited
    // network-instance key.
    deviation /oc-netinst:network-instances/oc-netinst:network-instance/oc-netinst:protocols/oc-netinst:protocol/oc-netinst:bgp/oc-netinst:neighbors/oc-netinst:neighbor {
      deviate add {
          sonic-ext:virtual-table "true";
          sonic-ext:db-name "CONFIG_DB";
          sonic-ext:subtree-transformer "ni_bgp_global_cfg_xfmr";
          sonic-ext:path-transformer "ni_bgp_list_path_xfmr";
      }
    }

    deviation /oc-netinst:network-instances/oc-netinst:network-instance/oc-netinst:protocols/oc-netinst:protocol/oc-netinst:bgp/oc-netinst:peer-groups/oc-netinst:peer-group {
      deviate add {
          sonic-ext:virtual-table "true";
          sonic-ext:db-name "CONFIG_DB";
          sonic-ext:subtree-transformer "ni_bgp_global_cfg_xfmr";
          sonic-ext:path-transformer "ni_bgp_list_path_xfmr";
      }
    }

    deviation /oc-netinst:network-instances/oc-netinst:network-instance/oc-netinst:table-connections {
      deviate add {
          sonic-ext:virtual-table "true";
          sonic-ext:db-name "CONFIG_DB";
          sonic-ext:subtree-transformer "ni_table_conn_cfg_xfmr";
      }
    }

    deviation /oc-netinst:network-instances/oc-netinst:network-instance/oc-netinst:table-connections/oc-netinst:table-connection {
      deviate add {
          sonic-ext:virtual-table "true";
          sonic-ext:db-name "CONFIG_DB";
          sonic-ext:subtree-transformer "ni_table_conn_cfg_xfmr";
      }
    }

    deviation /oc-netinst:network-instances/oc-netinst:network-instance/oc-netinst:table-connections/oc-netinst:table-connection/oc-netinst:src-protocol {
      deviate add {
          sonic-ext:db-name "CONFIG_DB";
          sonic-ext:subtree-transformer "ni_table_conn_cfg_xfmr";
      }
    }

    deviation /oc-netinst:network-instances/oc-netinst:network-instance/oc-netinst:table-connections/oc-netinst:table-connection/oc-netinst:dst-protocol {
      deviate add {
          sonic-ext:db-name "CONFIG_DB";
          sonic-ext:subtree-transformer "ni_table_conn_cfg_xfmr";
      }
    }

    deviation /oc-netinst:network-instances/oc-netinst:network-instance/oc-netinst:table-connections/oc-netinst:table-connection/oc-netinst:address-family {
      deviate add {
          sonic-ext:db-name "CONFIG_DB";
          sonic-ext:subtree-transformer "ni_table_conn_cfg_xfmr";
      }
    }

    deviation /oc-netinst:network-instances/oc-netinst:network-instance/oc-netinst:protocols/oc-netinst:protocol/oc-netinst:bgp/oc-netinst:global/oc-netinst:afi-safis/oc-netinst:afi-safi {
      deviate add {
          sonic-ext:virtual-table "true";
      }
    }

    deviation /oc-netinst:network-instances/oc-netinst:network-instance/oc-netinst:protocols/oc-netinst:protocol/oc-netinst:bgp/oc-netinst:global/oc-netinst:config {
      deviate add {
          sonic-ext:db-name "CONFIG_DB";
          sonic-ext:subtree-transformer "ni_bgp_global_cfg_xfmr";
      }
    }

    // A leaf-targeted GET dispatches via the leaf's own subtree transformer,
    // so each supported leaf must also carry the mapping (not just config).
    deviation /oc-netinst:network-instances/oc-netinst:network-instance/oc-netinst:protocols/oc-netinst:protocol/oc-netinst:bgp/oc-netinst:global/oc-netinst:config/oc-netinst:as {
      deviate add {
          sonic-ext:db-name "CONFIG_DB";
          sonic-ext:subtree-transformer "ni_bgp_global_cfg_xfmr";
      }
    }

    deviation /oc-netinst:network-instances/oc-netinst:network-instance/oc-netinst:protocols/oc-netinst:protocol/oc-netinst:bgp/oc-netinst:global/oc-netinst:config/oc-netinst:router-id {
      deviate add {
          sonic-ext:db-name "CONFIG_DB";
          sonic-ext:subtree-transformer "ni_bgp_global_cfg_xfmr";
      }
    }

    // BGP global operational state is published to STATE_DB by bgpmon as
    // BGP_GLOBALS_APPLIED|<network-instance>, sourced from the FRR summary
    // rather than CONFIG_DB, so aggregate GETs can merge as and router-id as
    // FRR holds them alongside total-paths and total-prefixes.
    deviation /oc-netinst:network-instances/oc-netinst:network-instance/oc-netinst:protocols/oc-netinst:protocol/oc-netinst:bgp/oc-netinst:global/oc-netinst:state {
      deviate add {
          sonic-ext:db-name "STATE_DB";
          sonic-ext:subtree-transformer "ni_bgp_global_state_xfmr";
      }
    }

    deviation /oc-netinst:network-instances/oc-netinst:network-instance/oc-netinst:protocols/oc-netinst:protocol/oc-netinst:bgp/oc-netinst:global/oc-netinst:state/oc-netinst:as {
      deviate add {
          sonic-ext:db-name "STATE_DB";
          sonic-ext:subtree-transformer "ni_bgp_global_state_xfmr";
      }
    }

    deviation /oc-netinst:network-instances/oc-netinst:network-instance/oc-netinst:protocols/oc-netinst:protocol/oc-netinst:bgp/oc-netinst:global/oc-netinst:state/oc-netinst:router-id {
      deviate add {
          sonic-ext:db-name "STATE_DB";
          sonic-ext:subtree-transformer "ni_bgp_global_state_xfmr";
      }
    }

    deviation /oc-netinst:network-instances/oc-netinst:network-instance/oc-netinst:protocols/oc-netinst:protocol/oc-netinst:bgp/oc-netinst:global/oc-netinst:state/oc-netinst:total-paths {
      deviate add {
          sonic-ext:db-name "STATE_DB";
          sonic-ext:subtree-transformer "ni_bgp_global_state_xfmr";
      }
    }

    deviation /oc-netinst:network-instances/oc-netinst:network-instance/oc-netinst:protocols/oc-netinst:protocol/oc-netinst:bgp/oc-netinst:global/oc-netinst:state/oc-netinst:total-prefixes {
      deviate add {
          sonic-ext:db-name "STATE_DB";
          sonic-ext:subtree-transformer "ni_bgp_global_state_xfmr";
      }
    }

    deviation /oc-netinst:network-instances/oc-netinst:network-instance/oc-netinst:protocols/oc-netinst:protocol/oc-netinst:bgp/oc-netinst:global/oc-netinst:route-selection-options/oc-netinst:config {
      deviate add {
          sonic-ext:db-name "CONFIG_DB";
          sonic-ext:subtree-transformer "ni_bgp_global_cfg_xfmr";
      }
    }

    deviation /oc-netinst:network-instances/oc-netinst:network-instance/oc-netinst:protocols/oc-netinst:protocol/oc-netinst:bgp/oc-netinst:global/oc-netinst:route-selection-options/oc-netinst:config/oc-netinst:always-compare-med {
      deviate add {
          sonic-ext:db-name "CONFIG_DB";
          sonic-ext:subtree-transformer "ni_bgp_global_cfg_xfmr";
      }
    }

    deviation /oc-netinst:network-instances/oc-netinst:network-instance/oc-netinst:protocols/oc-netinst:protocol/oc-netinst:bgp/oc-netinst:global/oc-netinst:use-multiple-paths/oc-netinst:ebgp/oc-netinst:config {
      deviate add {
          sonic-ext:db-name "CONFIG_DB";
          sonic-ext:subtree-transformer "ni_bgp_global_cfg_xfmr";
      }
    }

    deviation /oc-netinst:network-instances/oc-netinst:network-instance/oc-netinst:protocols/oc-netinst:protocol/oc-netinst:bgp/oc-netinst:global/oc-netinst:use-multiple-paths/oc-netinst:ebgp/oc-netinst:config/oc-netinst:maximum-paths {
      deviate add {
          sonic-ext:db-name "CONFIG_DB";
          sonic-ext:subtree-transformer "ni_bgp_global_cfg_xfmr";
      }
    }

    deviation /oc-netinst:network-instances/oc-netinst:network-instance/oc-netinst:protocols/oc-netinst:protocol/oc-netinst:bgp/oc-netinst:global/oc-netinst:use-multiple-paths/oc-netinst:ibgp/oc-netinst:config {
      deviate add {
          sonic-ext:db-name "CONFIG_DB";
          sonic-ext:subtree-transformer "ni_bgp_global_cfg_xfmr";
      }
    }

    deviation /oc-netinst:network-instances/oc-netinst:network-instance/oc-netinst:protocols/oc-netinst:protocol/oc-netinst:bgp/oc-netinst:global/oc-netinst:use-multiple-paths/oc-netinst:ibgp/oc-netinst:config/oc-netinst:maximum-paths {
      deviate add {
          sonic-ext:db-name "CONFIG_DB";
          sonic-ext:subtree-transformer "ni_bgp_global_cfg_xfmr";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ebgp/oc-netinst:config/oc-netinst:maximum-paths {
      deviate add {
          sonic-ext:db-name "CONFIG_DB";
          sonic-ext:subtree-transformer "ni_bgp_global_cfg_xfmr";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ibgp/oc-netinst:config/oc-netinst:maximum-paths {
      deviate add {
          sonic-ext:db-name "CONFIG_DB";
          sonic-ext:subtree-transformer "ni_bgp_global_cfg_xfmr";
      }
    }

    deviation /oc-netinst:network-instances/oc-netinst:network-instance/oc-netinst:protocols/oc-netinst:protocol/oc-netinst:bgp/oc-netinst:global/oc-netinst:afi-safis/oc-netinst:afi-safi/oc-netinst:config/oc-netinst:enabled {
      deviate add {
          sonic-ext:db-name "CONFIG_DB";
          sonic-ext:subtree-transformer "ni_bgp_global_cfg_xfmr";
      }
    }

    deviation /oc-netinst:network-instances/oc-netinst:network-instance/oc-netinst:protocols/oc-netinst:protocol/oc-netinst:bgp/oc-netinst:global/oc-netinst:afi-safis/oc-netinst:afi-safi/oc-netinst:ipv6-unicast/oc-netinst:config {
      deviate add {
          sonic-ext:db-name "CONFIG_DB";
          sonic-ext:subtree-transformer "ni_bgp_global_cfg_xfmr";
      }
    }

    deviation /oc-netinst:network-instances/oc-netinst:network-instance/oc-netinst:table-connections/oc-netinst:table-connection/oc-netinst:config {
      deviate add {
          sonic-ext:db-name "CONFIG_DB";
          sonic-ext:subtree-transformer "ni_table_conn_cfg_xfmr";
      }
    }

    deviation /oc-netinst:network-instances/oc-netinst:network-instance/oc-netinst:table-connections/oc-netinst:table-connection/oc-netinst:config/oc-netinst:src-protocol {
      deviate add {
          sonic-ext:db-name "CONFIG_DB";
          sonic-ext:subtree-transformer "ni_table_conn_cfg_xfmr";
      }
    }

    deviation /oc-netinst:network-instances/oc-netinst:network-instance/oc-netinst:table-connections/oc-netinst:table-connection/oc-netinst:config/oc-netinst:dst-protocol {
      deviate add {
          sonic-ext:db-name "CONFIG_DB";
          sonic-ext:subtree-transformer "ni_table_conn_cfg_xfmr";
      }
    }

    deviation /oc-netinst:network-instances/oc-netinst:network-instance/oc-netinst:table-connections/oc-netinst:table-connection/oc-netinst:config/oc-netinst:address-family {
      deviate add {
          sonic-ext:db-name "CONFIG_DB";
          sonic-ext:subtree-transformer "ni_table_conn_cfg_xfmr";
      }
    }

    deviation /oc-netinst:network-instances/oc-netinst:network-instance/oc-netinst:table-connections/oc-netinst:table-connection/oc-netinst:config/oc-netinst:import-policy {
      deviate add {
          sonic-ext:db-name "CONFIG_DB";
          sonic-ext:subtree-transformer "ni_table_conn_cfg_xfmr";
      }
    }

    deviation /oc-netinst:network-instances/oc-netinst:network-instance/oc-netinst:table-connections/oc-netinst:table-connection/oc-netinst:state {
      deviate add {
          sonic-ext:db-name "CONFIG_DB";
          sonic-ext:subtree-transformer "ni_table_conn_cfg_xfmr";
      }
    }

    deviation /oc-netinst:network-instances/oc-netinst:network-instance/oc-netinst:table-connections/oc-netinst:table-connection/oc-netinst:state/oc-netinst:src-protocol {
      deviate add {
          sonic-ext:db-name "CONFIG_DB";
          sonic-ext:subtree-transformer "ni_table_conn_cfg_xfmr";
      }
    }

    deviation /oc-netinst:network-instances/oc-netinst:network-instance/oc-netinst:table-connections/oc-netinst:table-connection/oc-netinst:state/oc-netinst:dst-protocol {
      deviate add {
          sonic-ext:db-name "CONFIG_DB";
          sonic-ext:subtree-transformer "ni_table_conn_cfg_xfmr";
      }
    }

    deviation /oc-netinst:network-instances/oc-netinst:network-instance/oc-netinst:table-connections/oc-netinst:table-connection/oc-netinst:state/oc-netinst:address-family {
      deviate add {
          sonic-ext:db-name "CONFIG_DB";
          sonic-ext:subtree-transformer "ni_table_conn_cfg_xfmr";
      }
    }

    deviation /oc-netinst:network-instances/oc-netinst:network-instance/oc-netinst:table-connections/oc-netinst:table-connection/oc-netinst:state/oc-netinst:import-policy {
      deviate add {
          sonic-ext:db-name "CONFIG_DB";
          sonic-ext:subtree-transformer "ni_table_conn_cfg_xfmr";
      }
    }


    deviation /oc-netinst:network-instances/oc-netinst:network-instance/oc-netinst:protocols/oc-netinst:protocol/oc-netinst:bgp/oc-netinst:neighbors/oc-netinst:neighbor/oc-netinst:config {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:config/oc-netinst:peer-group {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:config/oc-netinst:enabled {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:config/oc-netinst:peer-as {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:config/oc-netinst:send-community {
      deviate add {
          sonic-ext:db-name "CONFIG_DB";
          sonic-ext:subtree-transformer "ni_bgp_nbr_cfg_xfmr";
      }
    }

    // BGP neighbor operational state is published to STATE_DB by bgpmon as
    // NEIGH_STATE_TABLE|<neighbor-address>. It is a separate transformer from
    // the CONFIG_DB neighbor mapping so that the state subtree can offer
    // on-change subscription off the STATE_DB table.
    deviation /oc-netinst:network-instances/oc-netinst:network-instance/oc-netinst:protocols/oc-netinst:protocol/oc-netinst:bgp/oc-netinst:neighbors/oc-netinst:neighbor/oc-netinst:config/oc-netinst:auth-password {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:timers/oc-netinst:config {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:timers/oc-netinst:config/oc-netinst:connect-retry {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:timers/oc-netinst:config/oc-netinst:hold-time {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:timers/oc-netinst:config/oc-netinst:keepalive-interval {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:state {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:state/oc-netinst:session-state {
      deviate add {
          sonic-ext:db-name "STATE_DB";
          sonic-ext:subtree-transformer "ni_bgp_nbr_state_xfmr";
      }
    }

    // The remaining state leaves report the neighbor configuration as FRR
    // applied it, from BGP_NEIGH_APPLIED. They are served by the same
    // transformer as session-state because they share the state container, and
    // translib stops descending once a subtree transformer claims a node.
    deviation /oc-netinst:network-instances/oc-netinst:network-instance/oc-netinst:protocols/oc-netinst:protocol/oc-netinst:bgp/oc-netinst:neighbors/oc-netinst:neighbor/oc-netinst:state/oc-netinst:enabled {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:state/oc-netinst:neighbor-address {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:state/oc-netinst:peer-as {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:state/oc-netinst:peer-group {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:state/oc-netinst:supported-capabilities {
      deviate add {
          sonic-ext:db-name "STATE_DB";
          sonic-ext:subtree-transformer "ni_bgp_nbr_state_xfmr";
      }
    }

    // The per-session counters come from BGP_NEIGH_STATS, written by the same
    // bgpmon scrape that fills BGP_NEIGH_APPLIED. They are annotated onto the
    // same transformer for the same reason as the applied leaves: they share
    // the state container, which the transformer already claims.
    deviation /oc-netinst:network-instances/oc-netinst:network-instance/oc-netinst:protocols/oc-netinst:protocol/oc-netinst:bgp/oc-netinst:neighbors/oc-netinst:neighbor/oc-netinst:state/oc-netinst:established-transitions {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:state/oc-netinst:last-established {
      deviate add {
          sonic-ext:db-name "STATE_DB";
          sonic-ext:subtree-transformer "ni_bgp_nbr_state_xfmr";
      }
    }

    // The message counters sit below their own container rather than off the
    // state container, so each level is annotated. Only the UPDATE counters and
    // the received last-notification-error-code leaf are mapped today.
    deviation /oc-netinst:network-instances/oc-netinst:network-instance/oc-netinst:protocols/oc-netinst:protocol/oc-netinst:bgp/oc-netinst:neighbors/oc-netinst:neighbor/oc-netinst:state/oc-netinst:messages {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:state/oc-netinst:messages/oc-netinst:sent {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:state/oc-netinst:messages/oc-netinst:sent/oc-netinst:UPDATE {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:state/oc-netinst:messages/oc-netinst:received {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:state/oc-netinst:messages/oc-netinst:received/oc-netinst:UPDATE {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:state/oc-netinst:messages/oc-netinst:received/oc-netinst:last-notification-error-code {
      deviate add {
          sonic-ext:db-name "STATE_DB";
          sonic-ext:subtree-transformer "ni_bgp_nbr_state_xfmr";
      }
    }

    // transport/config is CONFIG_DB (local_addr, passive_mode). It must be
    // annotated onto the neighbor config transformer; otherwise it inherits
    // the transport container's STATE_DB annotation below and SET/DELETE
    // never reach BGP_NEIGHBOR. tcp-mss and mtu-discovery have no CONFIG_DB
    // field and are left unmapped.
    deviation /oc-netinst:network-instances/oc-netinst:network-instance/oc-netinst:protocols/oc-netinst:protocol/oc-netinst:bgp/oc-netinst:neighbors/oc-netinst:neighbor/oc-netinst:transport/oc-netinst:config {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:transport/oc-netinst:config/oc-netinst:local-address {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:transport/oc-netinst:config/oc-netinst:passive-mode {
      deviate add {
          sonic-ext:db-name "CONFIG_DB";
          sonic-ext:subtree-transformer "ni_bgp_nbr_cfg_xfmr";
      }
    }

    // The applied transport addresses come from the same row, so the transport
    // subtree is annotated onto the same transformer. Without an annotation
    // here the nearest annotated ancestor is the neighbor list, whose dispatch
    // maps CONFIG_DB only and would report nothing for these leaves.
    // transport/config is annotated separately above so SET/GET/DELETE of the
    // configured source address and passive-mode do not land here.
    deviation /oc-netinst:network-instances/oc-netinst:network-instance/oc-netinst:protocols/oc-netinst:protocol/oc-netinst:bgp/oc-netinst:neighbors/oc-netinst:neighbor/oc-netinst:transport {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:transport/oc-netinst:state {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:transport/oc-netinst:state/oc-netinst:local-address {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:transport/oc-netinst:state/oc-netinst:remote-address {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:transport/oc-netinst:state/oc-netinst:local-port {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:transport/oc-netinst:state/oc-netinst:remote-port {
      deviate add {
          sonic-ext:db-name "STATE_DB";
          sonic-ext:subtree-transformer "ni_bgp_nbr_state_xfmr";
      }
    }

    deviation /oc-netinst:network-instances/oc-netinst:network-instance/oc-netinst:protocols/oc-netinst:protocol/oc-netinst:bgp/oc-netinst:neighbors/oc-netinst:neighbor/oc-netinst:as-path-options/oc-netinst:config {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:as-path-options/oc-netinst:config/oc-netinst:allow-own-as {
      deviate add {
          sonic-ext:db-name "CONFIG_DB";
          sonic-ext:subtree-transformer "ni_bgp_nbr_cfg_xfmr";
      }
    }

    // The levels above the afi-safi config containers own themselves, so that a
    // request anchored on the container or on the list instance is served
    // rather than falling to the BGP container dispatch, which cannot delete.
    deviation /oc-netinst:network-instances/oc-netinst:network-instance/oc-netinst:protocols/oc-netinst:protocol/oc-netinst:bgp/oc-netinst:neighbors/oc-netinst:neighbor/oc-netinst:afi-safis {
      deviate add {
          sonic-ext:virtual-table "true";
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:afi-safis/oc-netinst:afi-safi {
      deviate add {
          sonic-ext:virtual-table "true";
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:afi-safi-name {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:afi-safi-name {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:enabled {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:send-community-type {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:import-policy {
      deviate add {
          sonic-ext:db-name "CONFIG_DB";
          sonic-ext:subtree-transformer "ni_bgp_nbr_cfg_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:export-policy {
      deviate add {
          sonic-ext:db-name "CONFIG_DB";
          sonic-ext:subtree-transformer "ni_bgp_nbr_cfg_xfmr";
      }
    }

    // apply-policy/state reports the route-maps FRR applies, which bgpmon
    // publishes on the family's BGP_NEIGH_AF_STATS row. That includes a policy
    // the neighbor inherits from its peer-group, which its own BGP_NEIGHBOR_AF
    // row does not carry. Without these the subtree inherits the config
    // annotation above and reads CONFIG_DB.
    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:state {
      deviate add {
          sonic-ext:db-name "STATE_DB";
          sonic-ext:subtree-transformer "ni_bgp_nbr_af_state_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:state/oc-netinst:import-policy {
      deviate add {
          sonic-ext:db-name "STATE_DB";
          sonic-ext:subtree-transformer "ni_bgp_nbr_af_state_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:state/oc-netinst:export-policy {
      deviate add {
          sonic-ext:db-name "STATE_DB";
          sonic-ext:subtree-transformer "ni_bgp_nbr_af_state_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:state/oc-netinst:default-import-policy {
      deviate add {
          sonic-ext:db-name "STATE_DB";
          sonic-ext:subtree-transformer "ni_bgp_nbr_af_state_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:state/oc-netinst:default-export-policy {
      deviate add {
          sonic-ext:db-name "STATE_DB";
          sonic-ext:subtree-transformer "ni_bgp_nbr_af_state_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:state {
      deviate add {
          sonic-ext:db-name "STATE_DB";
          sonic-ext:subtree-transformer "ni_bgp_nbr_af_state_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:state/oc-netinst:prefixes {
      deviate add {
          sonic-ext:db-name "STATE_DB";
          sonic-ext:subtree-transformer "ni_bgp_nbr_af_state_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:state/oc-netinst:prefixes/oc-netinst:received {
      deviate add {
          sonic-ext:db-name "STATE_DB";
          sonic-ext:subtree-transformer "ni_bgp_nbr_af_state_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:state/oc-netinst:prefixes/oc-netinst:received-pre-policy {
      deviate add {
          sonic-ext:db-name "STATE_DB";
          sonic-ext:subtree-transformer "ni_bgp_nbr_af_state_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:state/oc-netinst:prefixes/oc-netinst:sent {
      deviate add {
          sonic-ext:db-name "STATE_DB";
          sonic-ext:subtree-transformer "ni_bgp_nbr_af_state_xfmr";
      }
    }


    deviation /oc-netinst:network-instances/oc-netinst:network-instance/oc-netinst:protocols/oc-netinst:protocol/oc-netinst:bgp/oc-netinst:peer-groups/oc-netinst:peer-group/oc-netinst:config {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:config/oc-netinst:peer-group-name {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:config/oc-netinst:peer-as {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:timers/oc-netinst:config {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:timers/oc-netinst:config/oc-netinst:keepalive-interval {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:timers/oc-netinst:config/oc-netinst:hold-time {
      deviate add {
          sonic-ext:db-name "CONFIG_DB";
          sonic-ext:subtree-transformer "ni_bgp_pg_cfg_xfmr";
      }
    }

    // Peer-group state is what FRR applies, from STATE_DB. FRR reports only the
    // remote AS, the type and the activated families of a peer-group, so only
    // the leaves those back are served.
    deviation /oc-netinst:network-instances/oc-netinst:network-instance/oc-netinst:protocols/oc-netinst:protocol/oc-netinst:bgp/oc-netinst:peer-groups/oc-netinst:peer-group/oc-netinst:state {
      deviate add {
          sonic-ext:db-name "STATE_DB";
          sonic-ext:subtree-transformer "ni_bgp_pg_state_xfmr";
      }
    }

    deviation /oc-netinst:network-instances/oc-netinst:network-instance/oc-netinst:protocols/oc-netinst:protocol/oc-netinst:bgp/oc-netinst:peer-groups/oc-netinst:peer-group/oc-netinst:state/oc-netinst:peer-group-name {
      deviate add {
          sonic-ext:db-name "STATE_DB";
          sonic-ext:subtree-transformer "ni_bgp_pg_state_xfmr";
      }
    }

    deviation /oc-netinst:network-instances/oc-netinst:network-instance/oc-netinst:protocols/oc-netinst:protocol/oc-netinst:bgp/oc-netinst:peer-groups/oc-netinst:peer-group/oc-netinst:state/oc-netinst:peer-as {
      deviate add {
          sonic-ext:db-name "STATE_DB";
          sonic-ext:subtree-transformer "ni_bgp_pg_state_xfmr";
      }
    }

    deviation /oc-netinst:network-instances/oc-netinst:network-instance/oc-netinst:protocols/oc-netinst:protocol/oc-netinst:bgp/oc-netinst:peer-groups/oc-netinst:peer-group/oc-netinst:state/oc-netinst:peer-type {
      deviate add {
          sonic-ext:db-name "STATE_DB";
          sonic-ext:subtree-transformer "ni_bgp_pg_state_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state {
      deviate add {
          sonic-ext:db-name "STATE_DB";
          sonic-ext:subtree-transformer "ni_bgp_pg_state_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:afi-safi-name {
      deviate add {
          sonic-ext:db-name "STATE_DB";
          sonic-ext:subtree-transformer "ni_bgp_pg_state_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:enabled {
      deviate add {
          sonic-ext:db-name "STATE_DB";
          sonic-ext:subtree-transformer "ni_bgp_pg_state_xfmr";
      }
    }

    // The afi-safis container and the afi-safi list instance are named on the
    // peer-group config transformer, rather than left as bare virtual tables,
    // so that a request anchored on the container or on the list instance is
    // served rather than falling to the BGP container dispatch, which cannot
    // delete.
    deviation /oc-netinst:network-instances/oc-netinst:network-instance/oc-netinst:protocols/oc-netinst:protocol/oc-netinst:bgp/oc-netinst:peer-groups/oc-netinst:peer-group/oc-netinst:afi-safis {
      deviate add {
          sonic-ext:virtual-table "true";
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi {
      deviate add {
          sonic-ext:virtual-table "true";
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:afi-safi-name {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:afi-safi-name {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:enabled {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:send-community-type {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:config {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:config/oc-netinst:max-prefixes {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:config {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:config/oc-netinst:max-prefixes {
      deviate add {
          sonic-ext:db-name "CONFIG_DB";
          sonic-ext:subtree-transformer "ni_bgp_pg_cfg_xfmr";
      }
    }


    deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:export-policy {
      deviate add {
          sonic-ext:db-name "CONFIG_DB";
          sonic-ext:subtree-transformer "ni_bgp_pg_cfg_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:import-policy {
      deviate add {
          sonic-ext:db-name "CONFIG_DB";
          sonic-ext:subtree-transformer "ni_bgp_pg_cfg_xfmr";
      }
    }

    // Static routes of the STATIC protocol instance are stored in
    // CONFIG_DB:STATIC_ROUTE|<ni-name>|<prefix>. The protocol list itself is
    // annotated with the BGP transformer, which hands these requests over to
    // the static route mapping.
    deviation /oc-netinst:network-instances/oc-netinst:network-instance/oc-netinst:protocols/oc-netinst:protocol/oc-netinst:static-routes {
      deviate add {
          sonic-ext:virtual-table "true";
          sonic-ext:db-name "CONFIG_DB";
          sonic-ext:subtree-transformer "ni_static_route_cfg_xfmr";
      }
    }

    deviation /oc-netinst:network-instances/oc-netinst:network-instance/oc-netinst:protocols/oc-netinst:protocol/oc-netinst:static-routes/oc-netinst:static {
      deviate add {
          sonic-ext:virtual-table "true";
          sonic-ext:db-name "CONFIG_DB";
          sonic-ext:subtree-transformer "ni_static_route_cfg_xfmr";
          sonic-ext:path-transformer "ni_static_route_path_xfmr";
      }
    }

    deviation /oc-netinst:network-instances/oc-netinst:network-instance/oc-netinst:protocols/oc-netinst:protocol/oc-netinst:static-routes/oc-netinst:static/oc-netinst:prefix {
      deviate add {
          sonic-ext:db-name "CONFIG_DB";
          sonic-ext:subtree-transformer "ni_static_route_cfg_xfmr";
      }
    }

    deviation /oc-netinst:network-instances/oc-netinst:network-instance/oc-netinst:protocols/oc-netinst:protocol/oc-netinst:static-routes/oc-netinst:static/oc-netinst:config {
      deviate add {
          sonic-ext:db-name "CONFIG_DB";
          sonic-ext:subtree-transformer "ni_static_route_cfg_xfmr";
      }
    }

    deviation /oc-netinst:network-instances/oc-netinst:network-instance/oc-netinst:protocols/oc-netinst:protocol/oc-netinst:static-routes/oc-netinst:static/oc-netinst:config/oc-netinst:prefix {
      deviate add {
          sonic-ext:db-name "CONFIG_DB";
          sonic-ext:subtree-transformer "ni_static_route_cfg_xfmr";
      }
    }

    deviation /oc-netinst:network-instances/oc-netinst:network-instance/oc-netinst:protocols/oc-netinst:protocol/oc-netinst:static-routes/oc-netinst:static/oc-netinst:config/oc-netinst:set-tag {
      deviate add {
          sonic-ext:db-name "CONFIG_DB";
          sonic-ext:subtree-transformer "ni_static_route_cfg_xfmr";
      }
    }

    deviation /oc-netinst:network-instances/oc-netinst:network-instance/oc-netinst:protocols/oc-netinst:protocol/oc-netinst:static-routes/oc-netinst:static/oc-netinst:state {
      deviate add {
          sonic-ext:db-name "STATE_DB";
          sonic-ext:subtree-transformer "ni_static_route_cfg_xfmr";
      }
    }

    deviation /oc-netinst:network-instances/oc-netinst:network-instance/oc-netinst:protocols/oc-netinst:protocol/oc-netinst:static-routes/oc-netinst:static/oc-netinst:state/oc-netinst:prefix {
      deviate add {
          sonic-ext:db-name "STATE_DB";
          sonic-ext:subtree-transformer "ni_static_route_cfg_xfmr";
      }
    }

    deviation /oc-netinst:network-instances/oc-netinst:network-instance/oc-netinst:protocols/oc-netinst:protocol/oc-netinst:static-routes/oc-netinst:static/oc-netinst:state/oc-netinst:set-tag {
      deviate add {
          sonic-ext:db-name "STATE_DB";
          sonic-ext:subtree-transformer "ni_static_route_cfg_xfmr";
      }
    }

    deviation /oc-netinst:network-instances/oc-netinst:network-instance/oc-netinst:protocols/oc-netinst:protocol/oc-netinst:static-routes/oc-netinst:static/oc-netinst:next-hops {
      deviate add {
          sonic-ext:virtual-table "true";
          sonic-ext:db-name "CONFIG_DB";
          sonic-ext:subtree-transformer "ni_static_route_cfg_xfmr";
      }
    }

    deviation /oc-netinst:network-instances/oc-netinst:network-instance/oc-netinst:protocols/oc-netinst:protocol/oc-netinst:static-routes/oc-netinst:static/oc-netinst:next-hops/oc-netinst:next-hop {
      deviate add {
          sonic-ext:virtual-table "true";
          sonic-ext:db-name "CONFIG_DB";
          sonic-ext:subtree-transformer "ni_static_route_cfg_xfmr";
      }
    }

    deviation /oc-netinst:network-instances/oc-netinst:network-instance/oc-netinst:protocols/oc-netinst:protocol/oc-netinst:static-routes/oc-netinst:static/oc-netinst:next-hops/oc-netinst:next-hop/oc-netinst:index {
      deviate add {
          sonic-ext:db-name "CONFIG_DB";
          sonic-ext:subtree-transformer "ni_static_route_cfg_xfmr";
      }
    }

    deviation /oc-netinst:network-instances/oc-netinst:network-instance/oc-netinst:protocols/oc-netinst:protocol/oc-netinst:static-routes/oc-netinst:static/oc-netinst:next-hops/oc-netinst:next-hop/oc-netinst:config {
      deviate add {
          sonic-ext:db-name "CONFIG_DB";
          sonic-ext:subtree-transformer "ni_static_route_cfg_xfmr";
      }
    }

    deviation /oc-netinst:network-instances/oc-netinst:network-instance/oc-netinst:protocols/oc-netinst:protocol/oc-netinst:static-routes/oc-netinst:static/oc-netinst:next-hops/oc-netinst:next-hop/oc-netinst:config/oc-netinst:index {
      deviate add {
          sonic-ext:db-name "CONFIG_DB";
          sonic-ext:subtree-transformer "ni_static_route_cfg_xfmr";
      }
    }

    deviation /oc-netinst:network-instances/oc-netinst:network-instance/oc-netinst:protocols/oc-netinst:protocol/oc-netinst:static-routes/oc-netinst:static/oc-netinst:next-hops/oc-netinst:next-hop/oc-netinst:config/oc-netinst:next-hop {
      deviate add {
          sonic-ext:db-name "CONFIG_DB";
          sonic-ext:subtree-transformer "ni_static_route_cfg_xfmr";
      }
    }

    deviation /oc-netinst:network-instances/oc-netinst:network-instance/oc-netinst:protocols/oc-netinst:protocol/oc-netinst:static-routes/oc-netinst:static/oc-netinst:next-hops/oc-netinst:next-hop/oc-netinst:config/oc-netinst:preference {
      deviate add {
          sonic-ext:db-name "CONFIG_DB";
          sonic-ext:subtree-transformer "ni_static_route_cfg_xfmr";
      }
    }

    deviation /oc-netinst:network-instances/oc-netinst:network-instance/oc-netinst:protocols/oc-netinst:protocol/oc-netinst:static-routes/oc-netinst:static/oc-netinst:next-hops/oc-netinst:next-hop/oc-netinst:state {
      deviate add {
          sonic-ext:db-name "STATE_DB";
          sonic-ext:subtree-transformer "ni_static_route_cfg_xfmr";
      }
    }

    deviation /oc-netinst:network-instances/oc-netinst:network-instance/oc-netinst:protocols/oc-netinst:protocol/oc-netinst:static-routes/oc-netinst:static/oc-netinst:next-hops/oc-netinst:next-hop/oc-netinst:state/oc-netinst:index {
      deviate add {
          sonic-ext:db-name "STATE_DB";
          sonic-ext:subtree-transformer "ni_static_route_cfg_xfmr";
      }
    }

    deviation /oc-netinst:network-instances/oc-netinst:network-instance/oc-netinst:protocols/oc-netinst:protocol/oc-netinst:static-routes/oc-netinst:static/oc-netinst:next-hops/oc-netinst:next-hop/oc-netinst:state/oc-netinst:next-hop {
      deviate add {
          sonic-ext:db-name "STATE_DB";
          sonic-ext:subtree-transformer "ni_static_route_cfg_xfmr";
      }
    }

    deviation /oc-netinst:network-instances/oc-netinst:network-instance/oc-netinst:protocols/oc-netinst:protocol/oc-netinst:static-routes/oc-netinst:static/oc-netinst:next-hops/oc-netinst:next-hop/oc-netinst:state/oc-netinst:preference {
      deviate add {
          sonic-ext:db-name "STATE_DB";
          sonic-ext:subtree-transformer "ni_static_route_cfg_xfmr";
      }
    }

    // The AFT container reports the forwarding state fpmsyncd publishes to
    // APPL_DB. Each list below it is mapped by its own transformer; this one
    // answers a request on the container itself by fanning out to them, since
    // the infrastructure stops descending once a subtree transformer claims a
    // node.
    deviation /oc-netinst:network-instances/oc-netinst:network-instance/oc-netinst:afts {
      deviate add {
          sonic-ext:virtual-table "true";
          sonic-ext:db-name "APPL_DB";
          sonic-ext:subtree-transformer "ni_afts_xfmr";
      }
    }

    // The AFT next-hop list is the leafref target for the members of every
    // next-hop group, so it is keyed on the next-hop id FRR assigned, which
    // fpmsyncd publishes to APPL_DB. A next-hop reaches APPL_DB either inline
    // on a route in ROUTE_TABLE or as a member of a NEXTHOP_GROUP_TABLE row,
    // so this list is assembled from both tables and is independent of the
    // next-hop-group mapping.
    deviation /oc-netinst:network-instances/oc-netinst:network-instance/oc-netinst:afts/oc-netinst:next-hops {
      deviate add {
          sonic-ext:virtual-table "true";
          sonic-ext:db-name "APPL_DB";
          sonic-ext:subtree-transformer "ni_afts_next_hops_xfmr";
      }
    }

    deviation /oc-netinst:network-instances/oc-netinst:network-instance/oc-netinst:afts/oc-netinst:next-hops/oc-netinst:next-hop {
      deviate add {
          sonic-ext:virtual-table "true";
          sonic-ext:db-name "APPL_DB";
          sonic-ext:subtree-transformer "ni_afts_next_hops_xfmr";
      }
    }

    deviation /oc-netinst:network-instances/oc-netinst:network-instance/oc-netinst:afts/oc-netinst:next-hops/oc-netinst:next-hop/oc-netinst:index {
      deviate add {
          sonic-ext:db-name "APPL_DB";
          sonic-ext:subtree-transformer "ni_afts_next_hops_xfmr";
      }
    }

    deviation /oc-netinst:network-instances/oc-netinst:network-instance/oc-netinst:afts/oc-netinst:next-hops/oc-netinst:next-hop/oc-netinst:state {
      deviate add {
          sonic-ext:db-name "APPL_DB";
          sonic-ext:subtree-transformer "ni_afts_next_hops_xfmr";
      }
    }

    deviation /oc-netinst:network-instances/oc-netinst:network-instance/oc-netinst:afts/oc-netinst:next-hops/oc-netinst:next-hop/oc-netinst:state/oc-netinst:index {
      deviate add {
          sonic-ext:db-name "APPL_DB";
          sonic-ext:subtree-transformer "ni_afts_next_hops_xfmr";
      }
    }

    deviation /oc-netinst:network-instances/oc-netinst:network-instance/oc-netinst:afts/oc-netinst:next-hops/oc-netinst:next-hop/oc-netinst:state/oc-netinst:ip-address {
      deviate add {
          sonic-ext:db-name "APPL_DB";
          sonic-ext:subtree-transformer "ni_afts_next_hops_xfmr";
      }
    }

    deviation /oc-netinst:network-instances/oc-netinst:network-instance/oc-netinst:afts/oc-netinst:next-hops/oc-netinst:next-hop/oc-netinst:interface-ref {
      deviate add {
          sonic-ext:virtual-table "true";
          sonic-ext:db-name "APPL_DB";
          sonic-ext:subtree-transformer "ni_afts_next_hops_xfmr";
      }
    }

    deviation /oc-netinst:network-instances/oc-netinst:network-instance/oc-netinst:afts/oc-netinst:next-hops/oc-netinst:next-hop/oc-netinst:interface-ref/oc-netinst:state {
      deviate add {
          sonic-ext:db-name "APPL_DB";
          sonic-ext:subtree-transformer "ni_afts_next_hops_xfmr";
      }
    }

    deviation /oc-netinst:network-instances/oc-netinst:network-instance/oc-netinst:afts/oc-netinst:next-hops/oc-netinst:next-hop/oc-netinst:interface-ref/oc-netinst:state/oc-netinst:interface {
      deviate add {
          sonic-ext:db-name "APPL_DB";
          sonic-ext:subtree-transformer "ni_afts_next_hops_xfmr";
      }
    }

    // The AFT next-hop-group list maps NEXTHOP_GROUP_TABLE, whose Redis key is
    // the group id FRR assigned. Its members are named by the next-hop ids the
    // row lists, which are the keys of the next-hop list above.
    deviation /oc-netinst:network-instances/oc-netinst:network-instance/oc-netinst:afts/oc-netinst:next-hop-groups {
      deviate add {
          sonic-ext:virtual-table "true";
          sonic-ext:db-name "APPL_DB";
          sonic-ext:subtree-transformer "ni_afts_next_hop_groups_xfmr";
      }
    }

    // The path transformer turns the NEXTHOP_GROUP_TABLE key a keyspace
    // notification carries back into the path of the group it changed, which is
    // what lets the group level leaves be subscribed on change. It is inherited
    // by the nodes below, and refuses a path that reaches the member list, whose
    // key is held in a field value rather than in the Redis key.
    deviation /oc-netinst:network-instances/oc-netinst:network-instance/oc-netinst:afts/oc-netinst:next-hop-groups/oc-netinst:next-hop-group {
      deviate add {
          sonic-ext:virtual-table "true";
          sonic-ext:db-name "APPL_DB";
          sonic-ext:subtree-transformer "ni_afts_next_hop_groups_xfmr";
          sonic-ext:path-transformer "ni_afts_next_hop_groups_path_xfmr";
      }
    }

    deviation /oc-netinst:network-instances/oc-netinst:network-instance/oc-netinst:afts/oc-netinst:next-hop-groups/oc-netinst:next-hop-group/oc-netinst:id {
      deviate add {
          sonic-ext:db-name "APPL_DB";
          sonic-ext:subtree-transformer "ni_afts_next_hop_groups_xfmr";
      }
    }

    deviation /oc-netinst:network-instances/oc-netinst:network-instance/oc-netinst:afts/oc-netinst:next-hop-groups/oc-netinst:next-hop-group/oc-netinst:state {
      deviate add {
          sonic-ext:db-name "APPL_DB";
          sonic-ext:subtree-transformer "ni_afts_next_hop_groups_xfmr";
      }
    }

    deviation /oc-netinst:network-instances/oc-netinst:network-instance/oc-netinst:afts/oc-netinst:next-hop-groups/oc-netinst:next-hop-group/oc-netinst:state/oc-netinst:id {
      deviate add {
          sonic-ext:db-name "APPL_DB";
          sonic-ext:subtree-transformer "ni_afts_next_hop_groups_xfmr";
      }
    }

    deviation /oc-netinst:network-instances/oc-netinst:network-instance/oc-netinst:afts/oc-netinst:next-hop-groups/oc-netinst:next-hop-group/oc-netinst:next-hops {
      deviate add {
          sonic-ext:virtual-table "true";
          sonic-ext:db-name "APPL_DB";
          sonic-ext:subtree-transformer "ni_afts_next_hop_groups_xfmr";
      }
    }

    deviation /oc-netinst:network-instances/oc-netinst:network-instance/oc-netinst:afts/oc-netinst:next-hop-groups/oc-netinst:next-hop-group/oc-netinst:next-hops/oc-netinst:next-hop {
      deviate add {
          sonic-ext:virtual-table "true";
          sonic-ext:db-name "APPL_DB";
          sonic-ext:subtree-transformer "ni_afts_next_hop_groups_xfmr";
      }
    }

    deviation /oc-netinst:network-instances/oc-netinst:network-instance/oc-netinst:afts/oc-netinst:next-hop-groups/oc-netinst:next-hop-group/oc-netinst:next-hops/oc-netinst:next-hop/oc-netinst:index {
      deviate add {
          sonic-ext:db-name "APPL_DB";
          sonic-ext:subtree-transformer "ni_afts_next_hop_groups_xfmr";
      }
    }

    deviation /oc-netinst:network-instances/oc-netinst:network-instance/oc-netinst:afts/oc-netinst:next-hop-groups/oc-netinst:next-hop-group/oc-netinst:next-hops/oc-netinst:next-hop/oc-netinst:state {
      deviate add {
          sonic-ext:db-name "APPL_DB";
          sonic-ext:subtree-transformer "ni_afts_next_hop_groups_xfmr";
      }
    }

    deviation /oc-netinst:network-instances/oc-netinst:network-instance/oc-netinst:afts/oc-netinst:next-hop-groups/oc-netinst:next-hop-group/oc-netinst:next-hops/oc-netinst:next-hop/oc-netinst:state/oc-netinst:index {
      deviate add {
          sonic-ext:db-name "APPL_DB";
          sonic-ext:subtree-transformer "ni_afts_next_hop_groups_xfmr";
      }
    }

    deviation /oc-netinst:network-instances/oc-netinst:network-instance/oc-netinst:afts/oc-netinst:next-hop-groups/oc-netinst:next-hop-group/oc-netinst:next-hops/oc-netinst:next-hop/oc-netinst:state/oc-netinst:weight {
      deviate add {
          sonic-ext:db-name "APPL_DB";
          sonic-ext:subtree-transformer "ni_afts_next_hop_groups_xfmr";
      }
    }

    // The AFT IPv4 unicast entry list maps ROUTE_TABLE, whose Redis key is the
    // prefix. Only a route FRR resolved through a next-hop group carries a
    // group id, so state/next-hop-group is absent on a route that references
    // its single next-hop inline.
    deviation /oc-netinst:network-instances/oc-netinst:network-instance/oc-netinst:afts/oc-netinst:ipv4-unicast {
      deviate add {
          sonic-ext:virtual-table "true";
          sonic-ext:db-name "APPL_DB";
          sonic-ext:subtree-transformer "ni_afts_entries_xfmr";
      }
    }

    // The path transformer turns the ROUTE_TABLE key a keyspace notification
    // carries back into the path of the entry it changed, which is what lets
    // this list be subscribed on change. It is inherited by the nodes below.
    deviation /oc-netinst:network-instances/oc-netinst:network-instance/oc-netinst:afts/oc-netinst:ipv4-unicast/oc-netinst:ipv4-entry {
      deviate add {
          sonic-ext:virtual-table "true";
          sonic-ext:db-name "APPL_DB";
          sonic-ext:subtree-transformer "ni_afts_entries_xfmr";
          sonic-ext:path-transformer "ni_afts_entries_path_xfmr";
      }
    }

    deviation /oc-netinst:network-instances/oc-netinst:network-instance/oc-netinst:afts/oc-netinst:ipv4-unicast/oc-netinst:ipv4-entry/oc-netinst:prefix {
      deviate add {
          sonic-ext:db-name "APPL_DB";
          sonic-ext:subtree-transformer "ni_afts_entries_xfmr";
      }
    }

    deviation /oc-netinst:network-instances/oc-netinst:network-instance/oc-netinst:afts/oc-netinst:ipv4-unicast/oc-netinst:ipv4-entry/oc-netinst:state {
      deviate add {
          sonic-ext:db-name "APPL_DB";
          sonic-ext:subtree-transformer "ni_afts_entries_xfmr";
      }
    }

    deviation /oc-netinst:network-instances/oc-netinst:network-instance/oc-netinst:afts/oc-netinst:ipv4-unicast/oc-netinst:ipv4-entry/oc-netinst:state/oc-netinst:prefix {
      deviate add {
          sonic-ext:db-name "APPL_DB";
          sonic-ext:subtree-transformer "ni_afts_entries_xfmr";
      }
    }

    deviation /oc-netinst:network-instances/oc-netinst:network-instance/oc-netinst:afts/oc-netinst:ipv4-unicast/oc-netinst:ipv4-entry/oc-netinst:state/oc-netinst:next-hop-group {
      deviate add {
          sonic-ext:db-name "APPL_DB";
          sonic-ext:subtree-transformer "ni_afts_entries_xfmr";
      }
    }

    // ROUTE_TABLE holds both address families in one table, so the IPv6 entry
    // list is served by the same transformer as the IPv4 one and differs only
    // in the family it filters the rows on.
    deviation /oc-netinst:network-instances/oc-netinst:network-instance/oc-netinst:afts/oc-netinst:ipv6-unicast {
      deviate add {
          sonic-ext:virtual-table "true";
          sonic-ext:db-name "APPL_DB";
          sonic-ext:subtree-transformer "ni_afts_entries_xfmr";
      }
    }

    deviation /oc-netinst:network-instances/oc-netinst:network-instance/oc-netinst:afts/oc-netinst:ipv6-unicast/oc-netinst:ipv6-entry {
      deviate add {
          sonic-ext:virtual-table "true";
          sonic-ext:db-name "APPL_DB";
          sonic-ext:subtree-transformer "ni_afts_entries_xfmr";
          sonic-ext:path-transformer "ni_afts_entries_path_xfmr";
      }
    }

    deviation /oc-netinst:network-instances/oc-netinst:network-instance/oc-netinst:afts/oc-netinst:ipv6-unicast/oc-netinst:ipv6-entry/oc-netinst:prefix {
      deviate add {
          sonic-ext:db-name "APPL_DB";
          sonic-ext:subtree-transformer "ni_afts_entries_xfmr";
      }
    }

    deviation /oc-netinst:network-instances/oc-netinst:network-instance/oc-netinst:afts/oc-netinst:ipv6-unicast/oc-netinst:ipv6-entry/oc-netinst:state {
      deviate add {
          sonic-ext:db-name "APPL_DB";
          sonic-ext:subtree-transformer "ni_afts_entries_xfmr";
      }
    }

    deviation /oc-netinst:network-instances/oc-netinst:network-instance/oc-netinst:afts/oc-netinst:ipv6-unicast/oc-netinst:ipv6-entry/oc-netinst:state/oc-netinst:prefix {
      deviate add {
          sonic-ext:db-name "APPL_DB";
          sonic-ext:subtree-transformer "ni_afts_entries_xfmr";
      }
    }

    deviation /oc-netinst:network-instances/oc-netinst:network-instance/oc-netinst:afts/oc-netinst:ipv6-unicast/oc-netinst:ipv6-entry/oc-netinst:state/oc-netinst:next-hop-group {
      deviate add {
          sonic-ext:db-name "APPL_DB";
          sonic-ext:subtree-transformer "ni_afts_entries_xfmr";
      }
    }

}
