module openconfig-system-ext {

  yang-version "1";

  // namespace
  namespace "http://openconfig.net/yang/system-ext";

  prefix "oc-sys-ext";

  // import some basic types
  import openconfig-system { prefix oc-sys; }
  import openconfig-system-logging { prefix oc-log; }
  import openconfig-inet-types { prefix oc-inet; }
  import openconfig-extensions { prefix oc-ext; }
  import gnsi-credentialz { prefix gnsi-credz; }

  // meta
  organization "OpenConfig working group";

  contact
    "OpenConfig working group
    www.openconfig.net";

  description
    "This module adds vendor extensions to the base openconfig-system
    model to support management-plane features that are not covered by
    the upstream model:

      * a DSCP marking value for the SSH management server,
      * a DSCP marking value for TACACS+ client traffic,
      * an idle (inactivity) timeout for the serial console,
      * a source interface for NTP, TACACS+, and remote syslog
        management traffic, and
      * a disk-usage limit for automatic core file cleanup.";

  oc-ext:openconfig-version "0.4.0";

  revision "2026-09-23" {
    description
      "Add a core-file-cleanup container with a max-core-limit leaf
      (maps to AUTO_TECHSUPPORT|GLOBAL:max_core_limit).";
    reference "0.4.0";
  }

  revision "2026-09-01" {
    description
      "Add a dscp leaf to the AAA server-group config, used to mark
      TACACS+ client traffic (maps to TACPLUS|global:dscp).";
    reference "0.3.0";
  }

  revision "2026-08-27" {
    description
      "Add a source-interface leaf for NTP, TACACS+, and remote syslog
      logging (maps to the SONiC src_intf fields).";
    reference "0.2.0";
  }

  revision "2026-08-26" {
    description
      "Initial revision: SSH server DSCP marking and serial console
      idle timeout.";
    reference "0.1.0";
  }

  oc-ext:regexp-posix;
  oc-ext:catalog-organization "openconfig";
  oc-ext:origin "openconfig";

  // extension groupings

  grouping system-ssh-server-dscp-config {
    description
      "DSCP marking configuration for SSH management traffic.";

    leaf dscp {
      type oc-inet:dscp;
      description
        "DSCP value (0..63) used to mark packets originated by the SSH
        management server (control-plane traffic). Equivalent to the
        EOS 'management ssh / idle-timeout <n> qos dscp <dscp>'
        setting.";
    }
  }

  grouping system-console-timeout-config {
    description
      "Idle-timeout configuration for the serial console.";

    leaf timeout {
      type uint16;
      units seconds;
      description
        "Idle (inactivity) timeout in seconds for serial console
        sessions. A value of 0 disables the timeout. Equivalent to the
        EOS 'management console / idle-timeout <minutes>' setting.";
    }
  }

  grouping system-aaa-server-group-dscp-config {
    description
      "DSCP marking configuration for AAA client traffic.";

    leaf dscp {
      type oc-inet:dscp;
      description
        "DSCP value (0..63) used to mark packets originated by the
        AAA client towards the servers of this group. Only honored for
        TACACS+ groups, where it is equivalent to the EOS
        'tacacs-server qos dscp <dscp>' setting and maps to the SONiC
        TACPLUS|global:dscp field.";
    }
  }

  grouping system-source-interface-config {
    description
      "Source interface used to originate management-plane traffic for
      a service.";

    leaf source-interface {
      type string;
      description
        "Name of the interface (e.g. Loopback0) whose IP address is
        used as the source address for packets originated by this
        service. Equivalent to the EOS 'ntp local-interface <intf>' and
        'ip tacacs source-interface <intf>' settings; maps to the SONiC
        src_intf field of the corresponding global table.";
    }
  }

  grouping system-core-file-cleanup-config {
    description
      "Configuration for automatic cleanup of core files.";

    leaf max-core-limit {
      type decimal64 {
        fraction-digits 2;
        range "0..99.99";
      }
      units "percent";
      description
        "Maximum share of the filesystem hosting /var/core, in percent,
        that core files may occupy. When a new core file is written and
        the total size of the core files exceeds this limit, the oldest
        core files are deleted until the total is below it; the newest
        core file is always kept. A value of 0 disables this cleanup.
        Maps to the SONiC AUTO_TECHSUPPORT|GLOBAL:max_core_limit field.";
    }
  }

  grouping system-core-file-cleanup-state {
    description
      "Operational state for automatic cleanup of core files.";

    leaf enabled {
      type boolean;
      description
        "True when size-based core file cleanup runs, that is when the
        SONiC AUTO_TECHSUPPORT|GLOBAL:state field is 'enabled'. That field
        also gates event-driven tech-support collection, so it is not
        configurable through this container.";
    }
  }

  grouping system-core-file-cleanup-top {
    description
      "Top-level grouping for automatic core file cleanup.";

    container core-file-cleanup {
      description
        "Automatic cleanup of core files under /var/core.";

      container config {
        description
          "Configuration data for core file cleanup.";

        uses system-core-file-cleanup-config;
      }

      container state {
        config false;
        description
          "Operational state data for core file cleanup.";

        uses system-core-file-cleanup-config;
        uses system-core-file-cleanup-state;
      }
    }
  }

  // augment statements

  augment "/oc-sys:system/oc-sys:ssh-server/oc-sys:config" {
    description
      "Add DSCP marking to the SSH server configuration.";

    uses system-ssh-server-dscp-config;
  }

  augment "/oc-sys:system/oc-sys:ssh-server/oc-sys:state" {
    description
      "Add DSCP marking to the SSH server operational state.";

    uses system-ssh-server-dscp-config;
  }

  augment "/oc-sys:system/gnsi-credz:console/gnsi-credz:config" {
    description
      "Add an idle timeout to the serial console configuration. The
      console container itself is defined by gnsi-credentialz; this only
      adds the timeout leaf.";

    uses system-console-timeout-config;
  }

  augment "/oc-sys:system/gnsi-credz:console/gnsi-credz:state" {
    description
      "Add an idle timeout to the serial console operational state.";

    uses system-console-timeout-config;
  }

  augment "/oc-sys:system/oc-sys:ntp/oc-sys:config" {
    description
      "Add a source interface to the NTP client configuration.";

    uses system-source-interface-config;
  }

  augment "/oc-sys:system/oc-sys:ntp/oc-sys:state" {
    description
      "Add a source interface to the NTP client operational state.";

    uses system-source-interface-config;
  }

  augment "/oc-sys:system/oc-sys:aaa/oc-sys:server-groups/oc-sys:server-group/oc-sys:config" {
    description
      "Add a source interface and a DSCP marking value to the AAA
      server-group configuration. Only honored for TACACS+ groups,
      mapping to TACPLUS|global:src_intf and TACPLUS|global:dscp.";

    uses system-source-interface-config;
    uses system-aaa-server-group-dscp-config;
  }

  augment "/oc-sys:system/oc-sys:aaa/oc-sys:server-groups/oc-sys:server-group/oc-sys:state" {
    description
      "Add a source interface and a DSCP marking value to the AAA
      server-group operational state.";

    uses system-source-interface-config;
    uses system-aaa-server-group-dscp-config;
  }

  augment "/oc-sys:system/oc-log:logging" {
    description
      "Add a global source interface for remote syslog forwarding.
      The base openconfig-system-logging model has no global logging
      config container, so this extension adds config/state containers
      to hold the source-interface leaf (maps to
      SYSLOG_CONFIG|GLOBAL:src_intf).";

    container config {
      description
        "Global logging configuration extensions.";

      uses system-source-interface-config;
    }

    container state {
      config false;
      description
        "Global logging operational state extensions.";

      uses system-source-interface-config;
    }
  }

  augment "/oc-sys:system" {
    description
      "Add automatic core file cleanup configuration and state.";

    uses system-core-file-cleanup-top;
  }
}
